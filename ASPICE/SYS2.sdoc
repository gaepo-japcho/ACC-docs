[DOCUMENT]
TITLE: ACC SYS.2 System Requirements Analysis

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: TITLE
    TYPE: String
    REQUIRED: False
  - TITLE: STATEMENT
    TYPE: String
    REQUIRED: True
- TAG: REQUIREMENT
  FIELDS:
  - TITLE: UID
    TYPE: String
    REQUIRED: True
  - TITLE: TITLE
    TYPE: String
    REQUIRED: False
  - TITLE: STATEMENT
    TYPE: String
    REQUIRED: True
  - TITLE: ASIL
    TYPE: String
    REQUIRED: False
  - TITLE: CATEGORY
    TYPE: String
    REQUIRED: False
  - TITLE: VERIFICATION
    TYPE: String
    REQUIRED: False
  - TITLE: PRIORITY
    TYPE: String
    REQUIRED: False
  - TITLE: COMMENT
    TYPE: String
    REQUIRED: False
  RELATIONS:
  - TYPE: Parent

[TEXT]
STATEMENT: >>>
본 문서는 ASPICE SYS.2 (System Requirements Analysis) 프로세스에 따라, SYS.1에서 도출된 이해관계자 요구사항(STK)을 기반으로 시스템 요구사항을 분석·구조화하고, ISO 26262 안전 분석(HARA, Safety Goals, FSC)과의 연계를 기술한다.

- 프로젝트명: 1/10 스케일 RC카 기반 ACC 시스템
- 문서번호: ACC-SYS2-001
- 프로세스: ASPICE SYS.2 System Requirements Analysis
- 문서 버전: 1.0
- 작성일: 2026-03-31
- 프로젝트 기간: ~ 2026.04.30
- 팀 규모: 5명
- 적용 표준: ASPICE 4.0 / ISO 26262 / AUTOSAR

요구사항 추적 체인:
ELC (이해관계자 니즈) ← STK (이해관계자 요구사항) ← SYS (시스템 요구사항) ← SWR / HWR / SAF

본 문서에서 다루는 시스템 요구사항은 SYS.sdoc에 정의되어 있으며, 각 요구사항에는 UID, ASIL 등급, 카테고리, 검증 방법(T/A/I/R), 상위 추적성(Parent)이 태깅되어 있다. 본 문서는 이들 요구사항을 카테고리별로 분류·분석하고, 완전성·일관성·검증 가능성을 검토한 결과를 기술한다.

적용 범위: 1/10 스케일 RC카 기반 ACC 시스템 전체. 조향 기능(LKAS)과 AEB(자동 비상 제동)는 본 시스템 범위에 포함되지 않는다.
<<<

[[SECTION]]
TITLE: 기능 요구사항 분석

[TEXT]
STATEMENT: >>>
기능 요구사항은 ACC 시스템이 수행해야 하는 핵심 동작을 정의한다. STK(이해관계자 요구사항)에서 도출된 기능적 니즈를 시스템 수준으로 분해하였다. 기능 요구사항은 다음 하위 영역으로 분류된다: 상태 관리, 운전자 오버라이드, 안전거리 모델, 인식/측정, 운전자 인터페이스.
<<<

[REQUIREMENT]
UID: SYS2-FR-001
TITLE: 상태 전이 완전성 분석
STATEMENT: >>>
ACC 시스템은 5개 상태(OFF, STANDBY, CRUISING, FOLLOWING, FAULT)를 갖는 명확한 상태 머신으로 관리된다. 각 상태 전이 조건은 SYS001~SYS005에 정의되어 있으며, STK009(ACC 상태 관리), STK022(ACC ON 동작 흐름)에서 도출되었다.

상태 전이 모델 분석 결과:

- SYS001(OFF 전이): OFF에서 CRUISING/FOLLOWING으로의 전이 시 자가진단, 페달 입력 확인, 전방 차량 유무에 따른 분기를 모두 정의함. 안전거리 단계 기본값(3단계) 초기화 포함.
- SYS002(STANDBY 전이): SET/RES 버튼에 의한 재활성화 경로를 정의함. 이전 설정값 보존 메커니즘 포함.
- SYS003(CRUISING 전이): 전방 차량 감지 시 FOLLOWING 전이, 오버라이드/고장 시 전이 경로 완비.
- SYS004(FOLLOWING 전이): 전방 차량 소멸 시 CRUISING 복귀, 오버라이드/고장 시 전이 경로 완비. 최고속도 초과 방지 조건 포함.
- SYS005(FAULT 전이): 모터 출력 0(자연 감속), HMI 경고, ACC ON/OFF만 유효. ACC OFF에서 자가진단 실패 시 FAULT 진입 불가(OFF 유지).

모든 상태 간 전이 경로가 정의되어 있으며, 도달 불가 상태(unreachable state)나 데드락(deadlock)은 발견되지 않았다.
<<<
ASIL: B
CATEGORY: 분석
VERIFICATION: A
PRIORITY: 필수
RELATIONS:
- TYPE: Parent
  VALUE: SYS001
- TYPE: Parent
  VALUE: SYS002
- TYPE: Parent
  VALUE: SYS003
- TYPE: Parent
  VALUE: SYS004
- TYPE: Parent
  VALUE: SYS005

[REQUIREMENT]
UID: SYS2-FR-002
TITLE: 운전자 오버라이드 요구사항 분석
STATEMENT: >>>
운전자 오버라이드는 안전 최우선 원칙에 따라 어떤 상태에서든 운전자의 제동/가속 의지가 ACC보다 우선하도록 설계되었다. 브레이크 및 액셀 입력 시 모두 STANDBY로 전이하여 설정값을 보존하면서 운전자에게 즉시 제어권을 넘긴다.

분석 결과:

- SYS006(브레이크 오버라이드): 50ms 이내 STANDBY 전이. ASIL B. 설정값 보존.
- SYS007(가속 오버라이드): 50ms 이내 STANDBY 전이. ASIL QM. STANDBY 전이 자체는 가속 시나리오이므로 QM 적용 타당.
- SYS033(페달 입력 중 활성화 거부): 브레이크/액셀 페달이 눌린 상태에서 ACC ON 시도 시 거부. ASIL B.

오버라이드 응답 시간(50ms)은 1/10 스케일카의 물리적 특성(저속, 짧은 제동거리)을 고려할 때 충분한 안전 마진을 확보한다. STK007, STK008에서 도출됨.
<<<
ASIL: B
CATEGORY: 분석
VERIFICATION: A
PRIORITY: 필수
RELATIONS:
- TYPE: Parent
  VALUE: SYS006
- TYPE: Parent
  VALUE: SYS007
- TYPE: Parent
  VALUE: SYS033

[REQUIREMENT]
UID: SYS2-FR-003
TITLE: 안전거리 모델 분석
STATEMENT: >>>
안전거리 모델은 Time-gap 방식을 채택하여 자차 속도에 비례하는 목표 차간거리를 산출한다. 3단계(근거리/중거리/원거리)로 운전자가 선택 가능하다.

분석 결과:

- SYS008(1단계): 최소 안전거리 + Time-gap 0.8s * 자차속도. 근거리 추종.
- SYS009(2단계): 최소 안전거리 + Time-gap 1.2s * 자차속도. 중거리 추종.
- SYS010(3단계): 최소 안전거리 + Time-gap 1.6s * 자차속도. 원거리 추종. ACC 최초 활성화 시 기본값(SYS034).

1/10 스케일 기준 파라미터 튜닝이 필요하며, Simulink MBD 시뮬레이션 및 실차 테스트를 통해 최적값을 결정한다.

Time-gap 모델 적정성: 실차(1:1 스케일) ACC 시스템의 일반적 Time-gap 범위(1.0~2.0초)를 1/10 스케일에 맞게 조정한 값이다. 저속 주행 시 최소 거리(안전 마진)에 대한 추가 제한이 필요할 수 있으며, 이는 실차 튜닝 단계에서 결정한다.
<<<
ASIL: >>>
QM
<<<
CATEGORY: >>>
분석
<<<
VERIFICATION: >>>
A
<<<
PRIORITY: >>>
필수
<<<
RELATIONS:
- TYPE: Parent
  VALUE: SYS008
- TYPE: Parent
  VALUE: SYS009
- TYPE: Parent
  VALUE: SYS010
- TYPE: Parent
  VALUE: SYS034
- TYPE: Parent
  VALUE: SYS035

[REQUIREMENT]
UID: SYS2-FR-004
TITLE: 인식/측정 요구사항 분석
STATEMENT: >>>
분석 결과:

- SYS011(전방 차량 인식): 카메라(RPi) + LiDAR 융합. 카메라로 차량 유무 판별, LiDAR로 거리 확정. 센서 퓨전 방식 채택으로 단일 센서 대비 신뢰성 향상.
- SYS012(자차 속도 측정): 인코더 기반. 10ms 이하 주기, 1cm/s 분해능. Arduino 모터 제어 보드에서 계측 후 CAN 전송.
- SYS013(상대속도 산출): 메인 ECU에서 CAN 수신한 VEH_DIST의 시간 미분과 자차 속도를 조합하여 내부 산출. RPi/Arduino는 센서 I/O만 담당하며 상대속도 연산은 ECU가 수행한다(dumb I/O 아키텍처).

인식 파이프라인: RPi[카메라(차량 감지) + LiDAR(거리 측정) -> 센서 융합 -> CAN TX] -> 메인 ECU[수신 -> 상대속도 산출 -> 제어 연산]. 이 체인의 종단간 지연은 SYS020(100ms 이내)으로 제한된다.
<<<
ASIL: QM
CATEGORY: 분석
VERIFICATION: A
PRIORITY: 필수
RELATIONS:
- TYPE: Parent
  VALUE: SYS011
- TYPE: Parent
  VALUE: SYS012
- TYPE: Parent
  VALUE: SYS013

[REQUIREMENT]
UID: SYS2-FR-005
TITLE: 운전자 인터페이스 요구사항 분석
STATEMENT: >>>
분석 결과:

- SYS018(운전자 입력): RPi GUI 가상 버튼으로 모든 운전자 입력을 수신. CAN으로 메인 ECU 전달. 물리 버튼 없이 GUI로 통합함으로써 HW 복잡도 저감.
- SYS019(HMI 출력): GUI 클러스터에 현재 속도, ACC 상태, 설정값, FAULT 경고 표시. 상태별 그레이아웃 처리.
- SYS029(버튼 가용성): 상태별 활성/비활성 버튼 매트릭스 정의. 오조작 방지.
- SYS030(GUI->ECU CAN): 운전자 입력 CAN 전송 주기 20ms.
- SYS031(ECU->GUI CAN): HMI 표시 데이터 CAN 전송 주기 50ms.

GUI가 입력과 출력을 모두 담당하므로, RPi의 GUI 응답성과 CAN 통신 지연이 운전자 경험에 직접 영향을 미친다. GUI 갱신 지연은 사용자 인지에 크게 영향 없는 50ms 이내로 설계되었다.
<<<
ASIL: QM
CATEGORY: 분석
VERIFICATION: A
PRIORITY: 필수
RELATIONS:
- TYPE: Parent
  VALUE: SYS018
- TYPE: Parent
  VALUE: SYS019
- TYPE: Parent
  VALUE: SYS029
- TYPE: Parent
  VALUE: SYS030
- TYPE: Parent
  VALUE: SYS031

[REQUIREMENT]
UID: SYS2-FR-006
TITLE: 기타 기능 요구사항 분석
STATEMENT: >>>
분석 결과:

- SYS026(직진 전용): 조향 없이 직진만 가능. LKAS 범위 제외. 시스템 복잡도 감소.
- SYS027(SET/RES 복귀): STANDBY에서의 재활성화 경로. 사용자 편의성 확보.
- SYS028(일시정지): CRUISING/FOLLOWING에서 STANDBY 전이. 운전자 의도에 따른 일시 중단.
- SYS032(최소 설정 속도): 5cm/s 하한. 극저속에서의 ACC 동작 안정성 확보.
- SYS034(기본 안전거리 단계): OFF->활성화 시 3단계(원거리) 초기화. 보수적 안전 마진.
<<<
ASIL: QM
CATEGORY: 분석
VERIFICATION: A
PRIORITY: 필수
RELATIONS:
- TYPE: Parent
  VALUE: SYS026
- TYPE: Parent
  VALUE: SYS027
- TYPE: Parent
  VALUE: SYS028
- TYPE: Parent
  VALUE: SYS032
- TYPE: Parent
  VALUE: SYS034

[[/SECTION]]

[[SECTION]]
TITLE: 성능 요구사항 분석

[TEXT]
STATEMENT: >>>
성능 요구사항은 시스템의 응답 시간, 제어 정확도, 센서 갱신 주기 등 정량적 성능 지표를 정의한다. 1/10 스케일카의 물리적 특성(저속, 짧은 제동거리, 경량)을 반영하여 설정하였다.
<<<

[REQUIREMENT]
UID: SYS2-PR-001
TITLE: 제어 성능 요구사항 분석
STATEMENT: >>>
+-------------+--------------------------+------------+------+-----------------------------------------------------+
| 요구사항 ID | 항목                     | 목표값     | ASIL | 근거                                                |
+=============+==========================+============+======+=====================================================+
| SYS014      | PID 제어 주기            | 10ms       | QM   | Simulink MBD 코드 생성 기반, 정상 상태 오차 5% 이내 |
+-------------+--------------------------+------------+------+-----------------------------------------------------+
| SYS020      | 종단간 제어 응답 시간    | 100ms 이내 | B    | 전방 차량 감지 -> 제어 명령 출력까지의 지연         |
+-------------+--------------------------+------------+------+-----------------------------------------------------+
| SYS021      | LiDAR 갱신 주기          | 50ms 이내  | QM   | 거리 측정 데이터 갱신                               |
+-------------+--------------------------+------------+------+-----------------------------------------------------+
| SYS021      | 카메라 인식 주기         | 100ms 이내 | QM   | 차량 인식 처리 주기                                 |
+-------------+--------------------------+------------+------+-----------------------------------------------------+
| SYS006      | 브레이크 오버라이드 응답 | 50ms 이내  | B    | 운전자 제동 입력 -> STANDBY 전이                    |
+-------------+--------------------------+------------+------+-----------------------------------------------------+
| SYS007      | 액셀 오버라이드 응답     | 50ms 이내  | QM   | 운전자 가속 입력 -> STANDBY 전이                    |
+-------------+--------------------------+------------+------+-----------------------------------------------------+
| SYS012      | 속도 측정 주기           | 10ms 이내  | QM   | 인코더 기반 자차 속도 계측                          |
+-------------+--------------------------+------------+------+-----------------------------------------------------+
| SYS012      | 속도 분해능              | 1cm/s 이상 | QM   | 자차 속도 측정 정밀도                               |
+-------------+--------------------------+------------+------+-----------------------------------------------------+

타이밍 체인 분석:
- 센서 인식(100ms) -> CAN 전송(20ms) -> PID 계산(10ms) -> 모터 명령(10ms) = 총 약 140ms
- SYS020의 100ms 목표는 CAN 전송 후 제어 명령 출력까지의 시간을 의미하며, 센서 인식 시간은 별도이다.
- 브레이크 오버라이드(50ms)는 10ms 주기 태스크에서 매 주기 감시하므로, 최악 경우 10ms(태스크 지연) + CAN 전송 지연으로 50ms 이내 달성 가능.
<<<
ASIL: B
CATEGORY: 분석
VERIFICATION: A
PRIORITY: 필수
RELATIONS:
- TYPE: Parent
  VALUE: SYS014
- TYPE: Parent
  VALUE: SYS020
- TYPE: Parent
  VALUE: SYS021
- TYPE: Parent
  VALUE: SYS012

[[/SECTION]]

[[SECTION]]
TITLE: 안전 요구사항 분석 (FSR/TSR)

[TEXT]
STATEMENT: >>>
안전 요구사항은 ISO 26262에 따른 HARA에서 도출된 Safety Goals를 기능적 안전 요구사항(FSR) 및 기술적 안전 요구사항(TSR)으로 분해한 것이다. 상세 내용은 SAF.sdoc에 정의되어 있으며, 본 절에서는 분석 결과를 요약한다. 본 시스템은 AEB(자동 비상 제동)를 포함하지 않는다.
<<<

[REQUIREMENT]
UID: SYS2-SR-001
TITLE: FSR 분석 요약
STATEMENT: >>>
+--------+---------------------------------------------+------+------------------+------------+
| FSR ID | 요구사항                                    | ASIL | 관련 Safety Goal | 응답 시간  |
+========+=============================================+======+==================+============+
| SAF004 | 브레이크 시 모터 중지 -> STANDBY            | B    | SAF001, SAF003   | 50ms 이내  |
+--------+---------------------------------------------+------+------------------+------------+
| SAF015 | 액셀 시 STANDBY 전이                        | B    | SAF003           | 50ms 이내  |
+--------+---------------------------------------------+------+------------------+------------+
| SAF005 | 센서 고장 시 FAULT (능동 감속 없음)         | B    | SAF002           | 200ms 이내 |
+--------+---------------------------------------------+------+------------------+------------+
| SAF006 | CAN 통신 이상 시 FAULT (능동 감속 없음)     | B    | SAF001, SAF002   | 100ms 이내 |
+--------+---------------------------------------------+------+------------------+------------+
| SAF007 | 목표거리 이하 시 PID 최대 감속 (AEB 미포함) | QM   | SAF002           | -          |
+--------+---------------------------------------------+------+------------------+------------+
| SAF008 | 제어 출력 범위 제한                         | B    | SAF001           | -          |
+--------+---------------------------------------------+------+------------------+------------+
| SAF016 | ACC ON 시 자가진단 필수                     | B    | SAF001, SAF002   | -          |
+--------+---------------------------------------------+------+------------------+------------+
| SAF017 | 페달 입력 중 ACC 활성화 방지                | B    | SAF001, SAF003   | -          |
+--------+---------------------------------------------+------+------------------+------------+

FSR 완전성 분석:
- Safety Goal SAF001(의도치 않은 가속 방지): SAF004, SAF006, SAF008, SAF016, SAF017로 커버.
- Safety Goal SAF002(접근 시 감속): SAF005, SAF006, SAF007, SAF016으로 커버. AEB 미포함으로 비상 제동 없음.
- Safety Goal SAF003(운전자 오버라이드 보장): SAF004, SAF015, SAF017로 커버.

모든 Safety Goal이 하나 이상의 FSR로 분해되어 있음을 확인하였다.
<<<
ASIL: B
CATEGORY: 분석
VERIFICATION: A
PRIORITY: 필수
RELATIONS:
- TYPE: Parent
  VALUE: SYS005
- TYPE: Parent
  VALUE: SYS006
- TYPE: Parent
  VALUE: SYS022
- TYPE: Parent
  VALUE: SYS025

[REQUIREMENT]
UID: SYS2-SR-002
TITLE: TSR 분석 요약
STATEMENT: >>>
+--------+--------------------------------------------+------+--------------------------+
| TSR ID | 안전 메커니즘                              | ASIL | 대상                     |
+========+============================================+======+==========================+
| SAF009 | 브레이크 신호 이중화 (2GPIO, Fail-safe)    | B    | 브레이크 버튼 입력       |
+--------+--------------------------------------------+------+--------------------------+
| SAF010 | E2E P01 (RC+CRC, 선택적 적용)              | B    | ECU_PWM_CMD(0x200)만     |
+--------+--------------------------------------------+------+--------------------------+
| SAF011 | 워치독 타이머 (10ms 주기 킥)               | B    | 메인 ECU SW 행 감지      |
+--------+--------------------------------------------+------+--------------------------+
| SAF012 | 프로그램 흐름 모니터링                     | B    | 10ms 제어 루프 실행 순서 |
+--------+--------------------------------------------+------+--------------------------+
| SAF013 | RAM 무결성 테스트                          | B    | 안전 관련 RAM 영역       |
+--------+--------------------------------------------+------+--------------------------+
| SAF014 | 모터 구동 독립 차단 경로 (HW)              | B    | 모터 드라이버 Enable 핀  |
+--------+--------------------------------------------+------+--------------------------+

TSR은 FSR에서 요구하는 안전 동작을 구현하기 위한 구체적 기술 메커니즘이다. 특히 SAF014(독립 차단 경로)는 SW 고장 시에도 HW적으로 모터를 차단할 수 있는 최후 방어선 역할을 한다.
<<<
ASIL: B
CATEGORY: 분석
VERIFICATION: A
PRIORITY: 필수
RELATIONS:
- TYPE: Parent
  VALUE: SYS005
- TYPE: Parent
  VALUE: SYS006
- TYPE: Parent
  VALUE: SYS025

[[/SECTION]]

[[SECTION]]
TITLE: 인터페이스 요구사항 분석

[TEXT]
STATEMENT: >>>
인터페이스 요구사항은 시스템 내부 CAN 통신 메시지의 ID, 주기, DLC, 데이터 포맷을 정의한다. 모든 ECU 간 통신은 CAN 2.0B(500kbps)를 사용한다.
<<<

[REQUIREMENT]
UID: SYS2-IF-001
TITLE: CAN 통신 인터페이스 매트릭스
STATEMENT: >>>
+------------------------------+-------------+--------+-------+-------------------------------------------------------------+-----+
| 경로                         | 요구사항 ID | CAN ID | 주기  | 내용                                                        | DLC |
+==============================+=============+========+=======+=============================================================+=====+
| RPi -> 메인ECU (ACC명령)     | SYS030      | 0x100  | 20ms  | 액셀PWM(int8), 버튼5개(각 1bit), 목표속도(int8), 거리단계   | 8B  |
+------------------------------+-------------+--------+-------+-------------------------------------------------------------+-----+
| RPi -> 메인ECU (센서융합)    | SYS015      | 0x110  | 20ms  | 전방차량감지(1bit), 거리(16bit,mm)                          | 3B  |
+------------------------------+-------------+--------+-------+-------------------------------------------------------------+-----+
| RPi -> 메인ECU (하트비트)    | -           | 0x111  | 500ms | 하트비트 카운터(8bit), 오류 코드(8bit)                      | 2B  |
+------------------------------+-------------+--------+-------+-------------------------------------------------------------+-----+
| 메인ECU -> Arduino (모터)    | SYS016      | 0x200  | 10ms  | 4휠 개별 PWM 명령(각 int8, -128~127) + E2E P01(RC+CRC)      | 4B  |
+------------------------------+-------------+--------+-------+-------------------------------------------------------------+-----+
| Arduino -> 메인ECU (피드백)  | SYS017      | 0x300  | 10ms  | 4휠 인코더 속도(각 16bit, factor 0.01 cm/s)                 | 8B  |
+------------------------------+-------------+--------+-------+-------------------------------------------------------------+-----+
| Arduino -> 메인ECU (하트비트)| -           | 0x310  | 500ms | 하트비트 카운터(8bit), 오류 코드(8bit)                      | 2B  |
+------------------------------+-------------+--------+-------+-------------------------------------------------------------+-----+
| 메인ECU -> RPi GUI (HMI)     | SYS031      | 0x400  | 50ms  | 자차속도(16bit,0.01cm/s), ACC상태(8bit), 설정속도, 거리단계 | 5B  |
+------------------------------+-------------+--------+-------+-------------------------------------------------------------+-----+
| 메인ECU -> RPi+MTR (하트비트)| -           | 0x410  | 500ms | 하트비트 카운터(8bit), 오류 코드(8bit)                      | 2B  |
+------------------------------+-------------+--------+-------+-------------------------------------------------------------+-----+

CAN 고장 감지(SYS025): 3주기 연속 미수신 시 FAULT 전이. 타임아웃 값:
- 센서 데이터(20ms 주기): 60ms 타임아웃
- 모터 피드백(10ms 주기): 30ms 타임아웃
- GUI 입력(20ms 주기): 60ms 타임아웃

E2E 보호 정책(SAF010): AUTOSAR E2E Profile 01(Rolling Counter 4bit + CRC 8bit) 은 액추에이터 직접 제어 경로인 ECU_PWM_CMD(0x200) 에만 선택적 적용한다. 다른 CAN 메시지는 타임아웃 감시 및 수신 측 플러시블리티 검사로 무결성을 확보한다. 근거 및 구현 로드맵은 SYS2-QA-001 잔여 과제 #5 참조.
<<<
ASIL: B
CATEGORY: 분석
VERIFICATION: A
PRIORITY: 필수
RELATIONS:
- TYPE: Parent
  VALUE: SYS015
- TYPE: Parent
  VALUE: SYS016
- TYPE: Parent
  VALUE: SYS017
- TYPE: Parent
  VALUE: SYS025
- TYPE: Parent
  VALUE: SYS030
- TYPE: Parent
  VALUE: SYS031

[REQUIREMENT]
UID: SYS2-IF-002
TITLE: 센서 데이터 포맷 분석
STATEMENT: >>>
센서 데이터 포맷 (RPi -> 메인ECU, SYS015, SENSOR_FUSION 0x110, DLC=3B):

+--------+--------+---------------------+---------------+--------------+
| 바이트 | 비트   | 항목                | 단위          | 범위         |
+========+========+=====================+===============+==============+
| 0      | [0]    | VEH_DET (전방 차량 감지) | bool     | 0/1          |
+--------+--------+---------------------+---------------+--------------+
| 0      | [1-7]  | Reserved            | -             | 0            |
+--------+--------+---------------------+---------------+--------------+
| 1-2    | [0-15] | VEH_DIST (차간거리) | mm            | 0~12000      |
+--------+--------+---------------------+---------------+--------------+

상대속도는 SYS013에 따라 메인 ECU 내부에서 산출되므로 CAN 페이로드에 포함되지 않는다.

모터 명령 포맷 (메인ECU -> Arduino, SYS016, ECU_PWM_CMD 0x200, DLC=4B):

+--------+--------+---------------------+------+----------+
| 바이트 | 비트   | 항목                | 단위 | 범위     |
+========+========+=====================+======+==========+
| 0      | -      | SET_PWM_LF (좌전)   | int8 | -128~127 |
+--------+--------+---------------------+------+----------+
| 1      | -      | SET_PWM_RF (우전)   | int8 | -128~127 |
+--------+--------+---------------------+------+----------+
| 2      | -      | SET_PWM_LR (좌후)   | int8 | -128~127 |
+--------+--------+---------------------+------+----------+
| 3      | -      | SET_PWM_RR (우후)   | int8 | -128~127 |
+--------+--------+---------------------+------+----------+

양수=전진, 음수=후진. 30ms 무수신 시 모터 정지(ASIL-B 타임아웃, SYS016).

모터 피드백 포맷 (Arduino -> 메인ECU, SYS017, MTR_SPD_FB 0x300, DLC=8B):

+--------+--------+---------------------+--------------------+-------------------+
| 바이트 | 비트   | 항목                | 단위               | 범위              |
+========+========+=====================+====================+===================+
| 0-1    | [0-15] | GET_SPD_LF (좌전)   | cm/s (factor 0.01) | -327.68~327.67    |
+--------+--------+---------------------+--------------------+-------------------+
| 2-3    | [0-15] | GET_SPD_RF (우전)   | cm/s (factor 0.01) | -327.68~327.67    |
+--------+--------+---------------------+--------------------+-------------------+
| 4-5    | [0-15] | GET_SPD_LR (좌후)   | cm/s (factor 0.01) | -327.68~327.67    |
+--------+--------+---------------------+--------------------+-------------------+
| 6-7    | [0-15] | GET_SPD_RR (우후)   | cm/s (factor 0.01) | -327.68~327.67    |
+--------+--------+---------------------+--------------------+-------------------+

운전자 입력 포맷 (RPi GUI -> 메인ECU, SYS030, SENSOR_ACC_CMD 0x100, DLC=8B):

+--------+-------+----------------------------+-------+------------------------------+
| 바이트 | 비트  | 항목                       | 단위  | 범위                         |
+========+=======+============================+=======+==============================+
| 0      | -     | SET_ACCEL_PWM (액셀 PWM)   | int8  | -128~127                     |
+--------+-------+----------------------------+-------+------------------------------+
| 1      | [0]   | BTN_BRAKE (브레이크)       | bool  | 0/1 (눌림 유지=제동)         |
+--------+-------+----------------------------+-------+------------------------------+
| 1      | [1]   | BTN_ACC_OFF (ACC OFF)      | bool  | 0/1 (엣지 트리거)            |
+--------+-------+----------------------------+-------+------------------------------+
| 1      | [2]   | BTN_ACC_SET (SET)          | bool  | 0/1 (엣지 트리거)            |
+--------+-------+----------------------------+-------+------------------------------+
| 1      | [3]   | BTN_ACC_RES (RESUME)       | bool  | 0/1 (엣지 트리거)            |
+--------+-------+----------------------------+-------+------------------------------+
| 1      | [4]   | BTN_ACC_CANCEL (CANCEL)    | bool  | 0/1 (엣지 트리거)            |
+--------+-------+----------------------------+-------+------------------------------+
| 1      | [5-7] | Reserved                   | -     | 0                            |
+--------+-------+----------------------------+-------+------------------------------+
| 2      | -     | SET_ACC_SPD (목표 속도)    | int8  | -128~127 cm/s                |
+--------+-------+----------------------------+-------+------------------------------+
| 3      | -     | SET_ACC_LVL (거리 단계)    | uint8 | 1=CLOSE, 2=MEDIUM, 3=FAR     |
+--------+-------+----------------------------+-------+------------------------------+
| 4-7    | -     | Reserved                   | -     | 0                            |
+--------+-------+----------------------------+-------+------------------------------+

HMI 표시 데이터 포맷 (메인ECU -> RPi GUI, SYS031, ECU_ACC_STATUS 0x400, DLC=5B):

+--------+--------+--------------------+--------------------+------------------------------------------------+
| 바이트 | 비트   | 항목               | 단위               | 범위                                           |
+========+========+====================+====================+================================================+
| 0-1    | [0-15] | GET_SPD_AVG        | cm/s (factor 0.01) | -327.68~327.67                                 |
+--------+--------+--------------------+--------------------+------------------------------------------------+
| 2      | -      | GET_ACC_STATUS     | enum               | 0=OFF,1=STANDBY,2=CRUISING,3=FOLLOWING,4=FAULT |
+--------+--------+--------------------+--------------------+------------------------------------------------+
| 3      | -      | GET_ACC_SPD        | int8 cm/s          | -128~127                                       |
+--------+--------+--------------------+--------------------+------------------------------------------------+
| 4      | -      | GET_ACC_LVL        | uint8              | 1=CLOSE, 2=MEDIUM, 3=FAR                       |
+--------+--------+--------------------+--------------------+------------------------------------------------+
<<<
ASIL: QM
CATEGORY: 분석
VERIFICATION: A
PRIORITY: 필수
RELATIONS:
- TYPE: Parent
  VALUE: SYS015
- TYPE: Parent
  VALUE: SYS016
- TYPE: Parent
  VALUE: SYS030
- TYPE: Parent
  VALUE: SYS031

[[/SECTION]]

[[SECTION]]
TITLE: 비기능 요구사항 분석

[TEXT]
STATEMENT: >>>
비기능 요구사항은 시스템의 아키텍처 제약, 개발 프로세스, 진단 기능 등을 정의한다.
<<<

[REQUIREMENT]
UID: SYS2-NF-001
TITLE: 비기능 요구사항 분석
STATEMENT: >>>
+-------------+--------------------+---------------------------------------+------+
| 요구사항 ID | 항목               | 내용                                  | ASIL |
+=============+====================+=======================================+======+
| SYS023      | AUTOSAR 준수       | ASW/RTE/BSW 계층 구조. mobilgene 활용 | QM   |
+-------------+--------------------+---------------------------------------+------+
| SYS024      | MBD 기반 제어 설계 | MATLAB/Simulink MBD. 자동 코드 생성   | QM   |
+-------------+--------------------+---------------------------------------+------+
| SYS026      | 직진 전용 차량     | 조향 없음. LKAS 범위 제외             | QM   |
+-------------+--------------------+---------------------------------------+------+

추가 비기능 고려사항:

진단(DTC): MVP 범위 외 (SWR017 철회, 2026-04-21). 본 시스템은 SWR016 의 FAULT 전이·HMI 경고만 제공하며, BSW Dem 연동·DTC NV 저장은 구현하지 않는다.

전원 모드 대응: 본 시스템은 배터리 구동 RC카이므로, 저전압(배터리 부족) 감지 시 FAULT 전이를 권장한다. (향후 요구사항 추가 검토 필요)

EMC 내성: 1/10 스케일 학생 프로젝트 특성상 별도의 EMC 시험은 수행하지 않으나, CAN 트랜시버(MCP2551/TJA1050)의 내장 EMC 보호 기능에 의존한다.

온도 범위: 실내 환경(15~35도) 운영을 기본으로 한다. 극한 온도 시험은 범위 외.
<<<
ASIL: QM
CATEGORY: 분석
VERIFICATION: A
PRIORITY: 필수
RELATIONS:
- TYPE: Parent
  VALUE: SYS023
- TYPE: Parent
  VALUE: SYS024
- TYPE: Parent
  VALUE: SYS026

[[/SECTION]]

[[SECTION]]
TITLE: 요구사항 속성 및 추적성

[TEXT]
STATEMENT: >>>
모든 시스템 요구사항에는 다음 속성이 태깅되어 있으며, 상위(STK) 및 하위(SWR/HWR/SAF) 요구사항과의 양방향 추적성을 확보한다.
<<<

[REQUIREMENT]
UID: SYS2-AT-001
TITLE: 요구사항 속성 체계
STATEMENT: >>>
각 시스템 요구사항(SYS)의 속성 체계:

+--------------+-----------------------+------------------------------------------------+
| 속성         | 설명                  | 예시                                           |
+==============+=======================+================================================+
| UID          | 고유 식별자           | SYS001, SYS002, ...                            |
+--------------+-----------------------+------------------------------------------------+
| TITLE        | 요구사항 제목         | ACC 상태 전이 - OFF                            |
+--------------+-----------------------+------------------------------------------------+
| STATEMENT    | 요구사항 상세 기술    | (본문)                                         |
+--------------+-----------------------+------------------------------------------------+
| ASIL         | ISO 26262 ASIL 등급   | QM, B                                          |
+--------------+-----------------------+------------------------------------------------+
| CATEGORY     | 요구사항 분류         | 기능, 안전, 성능, 인터페이스, 비기능           |
+--------------+-----------------------+------------------------------------------------+
| VERIFICATION | 검증 방법             | T(Test), A(Analysis), I(Inspection), R(Review) |
+--------------+-----------------------+------------------------------------------------+
| Parent       | 상위 추적성 (STK UID) | STK001, STK009, ...                            |
+--------------+-----------------------+------------------------------------------------+

추적 체계 검증 결과:
- 모든 SYS 요구사항은 최소 1개의 STK Parent를 보유하여 상위 추적성 확보
- 모든 STK 요구사항은 최소 1개의 SYS에 의해 참조되어 도출 완전성 확보
- ASIL 상속: 상위(STK) 요구사항이 안전 관련이면 하위(SYS)에 적절한 ASIL 태깅
- 검증 방법 할당: 모든 SYS 요구사항에 T/A/I/R 중 최소 1개 할당
<<<
ASIL: QM
CATEGORY: 분석
VERIFICATION: A
PRIORITY: 필수
RELATIONS:
- TYPE: Parent
  VALUE: SYS001

[REQUIREMENT]
UID: SYS2-AT-002
TITLE: 요구사항 카테고리별 분포
STATEMENT: >>>
시스템 요구사항 카테고리별 분포 분석:

+------------+------+--------------------------------------------------------------------+------------------------+
| 카테고리   | 수량 | 요구사항 ID                                                        | ASIL B 포함            |
+============+======+====================================================================+========================+
| 기능       | 17   | SYS001~005, SYS008~010, SYS011, SYS013, SYS026~029, SYS032, SYS034 | SYS004, SYS005         |
+------------+------+--------------------------------------------------------------------+------------------------+
| 안전       | 3    | SYS006, SYS022, SYS033                                             | SYS006, SYS022, SYS033 |
+------------+------+--------------------------------------------------------------------+------------------------+
| 성능       | 4    | SYS012, SYS014, SYS020, SYS021                                     | SYS020                 |
+------------+------+--------------------------------------------------------------------+------------------------+
| 인터페이스 | 7    | SYS015~019, SYS030, SYS031                                         | 없음                   |
+------------+------+--------------------------------------------------------------------+------------------------+
| 비기능     | 2    | SYS023, SYS024                                                     | 없음                   |
+------------+------+--------------------------------------------------------------------+------------------------+
| 합계       | 33   | -                                                                  | 6                      |
+------------+------+--------------------------------------------------------------------+------------------------+

ASIL 분포: ASIL B = 6건, QM = 27건. 1/10 스케일 학생 프로젝트 특성을 반영하여 안전 관련 핵심 요구사항에 집중적으로 ASIL B를 할당하였다.
<<<
ASIL: QM
CATEGORY: 분석
VERIFICATION: A
PRIORITY: 필수
RELATIONS:
- TYPE: Parent
  VALUE: SYS001

[REQUIREMENT]
UID: SYS2-AT-003
TITLE: 검증 방법 매트릭스
STATEMENT: >>>
시스템 요구사항 검증 방법 분포:

+------------+------+------------------+---------------------------------------------+
| 검증 방법  | 약어 | 적용 요구사항 수 | 대상                                        |
+============+======+==================+=============================================+
| Test       | T    | 27               | 기능 동작, 성능, 안전 요구사항              |
+------------+------+------------------+---------------------------------------------+
| Analysis   | A    | 0                | (시스템 수준에서는 T/I 위주)                |
+------------+------+------------------+---------------------------------------------+
| Inspection | I    | 4                | AUTOSAR 준수, MBD 설계, 직진 전용, HMI 표시 |
+------------+------+------------------+---------------------------------------------+
| Review     | R    | 0                | (문서 리뷰는 프로세스 차원에서 수행)        |
+------------+------+------------------+---------------------------------------------+

Test(T) 대상 요구사항은 통합 테스트 시나리오에서 검증한다. 주요 테스트 카테고리:
- 상태 전이 테스트 (SYS001~005)
- 오버라이드 응답 시간 테스트 (SYS006, SYS007)
- 안전거리 제어 테스트 (SYS008~010)
- CAN 통신 정상/이상 테스트 (SYS015~017, SYS025)
- FAULT 진입/복귀 테스트 (SYS005, SYS025)
<<<
ASIL: QM
CATEGORY: 분석
VERIFICATION: A
PRIORITY: 필수
RELATIONS:
- TYPE: Parent
  VALUE: SYS001

[[/SECTION]]

[[SECTION]]
TITLE: ISO 26262 연계 - HARA (Hazard Analysis and Risk Assessment)

[TEXT]
STATEMENT: >>>
ISO 26262 Part 3에 따라, ACC 시스템의 위험 상황을 식별하고 Severity(S), Exposure(E), Controllability(C) 평가를 통해 ASIL을 도출하였다.
<<<

[REQUIREMENT]
UID: SYS2-HARA-001
TITLE: HARA 결과 요약
STATEMENT: >>>
위험 분석 대상: 1/10 스케일 RC카 ACC 시스템

+-----------+-------------------------------------------------+----------+----------+-----------------+------+
| Hazard ID | 위험 상황                                       | Severity | Exposure | Controllability | ASIL |
+===========+=================================================+==========+==========+=================+======+
| H-001     | 의도치 않은 가속 (ACC 오동작으로 불필요한 가속) | S2       | E3       | C2              | B    |
+-----------+-------------------------------------------------+----------+----------+-----------------+------+
| H-002     | 전방 차량 접근 시 감속 실패 (충돌 위험)         | S2       | E3       | C2              | B    |
+-----------+-------------------------------------------------+----------+----------+-----------------+------+
| H-003     | 운전자 오버라이드 불가 (브레이크/액셀 무시)     | S2       | E4       | C1              | B    |
+-----------+-------------------------------------------------+----------+----------+-----------------+------+

Severity 근거 (S2):
- 1/10 스케일카이므로 인체 직접 상해 가능성은 낮음 (S1~S2)
- 고속 충돌 시 차량 파손 및 주변 물체 손상 가능성 고려하여 S2 적용

Exposure 근거 (E3~E4):
- E3: ACC 동작 중 전방 차량 존재 시나리오는 빈번함
- E4: 운전자가 브레이크/액셀을 사용하는 상황은 매우 빈번함

Controllability 근거 (C1~C2):
- C1: 운전자가 직접 차량을 잡거나 전원을 끌 수 있음 (1/10 스케일 특성)
- C2: 고속 주행 시 즉시 개입이 어려울 수 있음

ASIL 결정: S2/E3/C2 -> ASIL B, S2/E4/C1 -> ASIL B
본 시스템의 최대 ASIL은 B이다.
<<<
ASIL: B
CATEGORY: HARA
VERIFICATION: A
PRIORITY: 필수
RELATIONS:
- TYPE: Parent
  VALUE: SYS001

[[/SECTION]]

[[SECTION]]
TITLE: ISO 26262 연계 - Safety Goals

[TEXT]
STATEMENT: >>>
HARA에서 도출된 위험을 방지하기 위한 최상위 안전 목표(Safety Goals)를 정의한다. Safety Goals는 SAF.sdoc에 상세 정의되어 있다.
<<<

[REQUIREMENT]
UID: SYS2-SG-001
TITLE: Safety Goals 요약 및 분석
STATEMENT: >>>
+----------------+-------------------------------------------------------------+------+------------------+----------------------------+-------+
| Safety Goal ID | 안전 목표                                                   | ASIL | HARA 근거        | Safe State                 | FTTI  |
+================+=============================================================+======+==================+============================+=======+
| SAF001         | ACC는 의도치 않은 가속을 야기해서는 안 된다                 | B    | H-001 (S2/E3/C2) | 모터 구동 중지 (ACC OFF)   | 100ms |
+----------------+-------------------------------------------------------------+------+------------------+----------------------------+-------+
| SAF002         | 전방 차량 접근 시 PID 범위 내 적절한 감속 수행 (AEB 미포함) | B    | H-002 (S2/E3/C2) | 모터 출력 0 (자연 감속)    | 200ms |
+----------------+-------------------------------------------------------------+------+------------------+----------------------------+-------+
| SAF003         | 운전자의 브레이크/액셀 입력은 어떤 상황에서도 ACC보다 우선  | B    | H-003 (S2/E4/C1) | 운전자 직접 제어 (STANDBY) | 50ms  |
+----------------+-------------------------------------------------------------+------+------------------+----------------------------+-------+

Safety Goal 충족 검증:
- SAF001 -> FSR: SAF004, SAF006, SAF008, SAF016, SAF017 (5건)
- SAF002 -> FSR: SAF005, SAF006, SAF007, SAF016 (4건)
- SAF003 -> FSR: SAF004, SAF015, SAF017 (3건)

모든 Safety Goal이 FSR로 분해되었으며, 각 FSR은 SYS 요구사항에 대한 추적성을 보유한다.

FTTI(Fault Tolerant Time Interval) 근거:
- SAF001(100ms): 의도치 않은 가속 발생 시 100ms 이내 감지 및 모터 정지
- SAF002(200ms): 전방 차량 접근 시 200ms 이내 감속 개시 (센서 지연 포함)
- SAF003(50ms): 운전자 입력 후 50ms 이내 STANDBY 전이 (즉각 응답 필요)
<<<
ASIL: B
CATEGORY: Safety Goal
VERIFICATION: A
PRIORITY: 필수
RELATIONS:
- TYPE: Parent
  VALUE: SYS005
- TYPE: Parent
  VALUE: SYS006
- TYPE: Parent
  VALUE: SYS007

[[/SECTION]]

[[SECTION]]
TITLE: ISO 26262 연계 - FSC (Functional Safety Concept)

[TEXT]
STATEMENT: >>>
Functional Safety Concept(FSC)는 Safety Goals를 기능적 안전 요구사항으로 분해하고, 이를 구현하기 위한 안전 메커니즘을 정의한다.
<<<

[REQUIREMENT]
UID: SYS2-FSC-001
TITLE: Functional Safety Concept 분석
STATEMENT: >>>
Safety Goal -> FSR -> 안전 메커니즘 분해 구조:

+-----------------------------------+--------+---------------------------------------------+--------------------------------------------------+
| Safety Goal                       | FSR ID | FSR 내용                                    | 안전 메커니즘                                    |
+===================================+========+=============================================+==================================================+
| SAF001 (의도치 않은 가속 방지)    | SAF004 | 브레이크 시 모터 즉시 중지, STANDBY 전이    | 10ms 주기 브레이크 감시 + 이중 GPIO 읽기(SAF009) |
+-----------------------------------+--------+---------------------------------------------+--------------------------------------------------+
| SAF001                            | SAF006 | CAN 통신 이상 시 FAULT, 모터 출력 0         | CAN 타임아웃 감시 + E2E P01 on MTR_CMD (SAF010)  |
+-----------------------------------+--------+---------------------------------------------+--------------------------------------------------+
| SAF001                            | SAF008 | 제어 출력 범위 제한                         | PID 출력 클램핑 (최대 가속도/감속도 제한)        |
+-----------------------------------+--------+---------------------------------------------+--------------------------------------------------+
| SAF001                            | SAF016 | ACC ON 시 자가진단                          | CAN 응답 확인 + 센서 유효성 + 페달 상태 확인     |
+-----------------------------------+--------+---------------------------------------------+--------------------------------------------------+
| SAF001                            | SAF017 | 페달 입력 중 활성화 방지                    | 브레이크/액셀 상태 선확인 후 ACC ON 허용         |
+-----------------------------------+--------+---------------------------------------------+--------------------------------------------------+
| SAF002 (접근 시 감속, AEB 미포함) | SAF005 | 센서 고장 시 FAULT, 모터 출력 0             | CAN 타임아웃 + 센서 데이터 유효성 검사           |
+-----------------------------------+--------+---------------------------------------------+--------------------------------------------------+
| SAF002                            | SAF006 | CAN 통신 이상 시 FAULT (공유)               | (상동)                                           |
+-----------------------------------+--------+---------------------------------------------+--------------------------------------------------+
| SAF002                            | SAF007 | 목표거리 이하 시 PID 최대 감속 (AEB 미포함) | PID 제어 범위 내 최대 감속, 비상 제동 없음       |
+-----------------------------------+--------+---------------------------------------------+--------------------------------------------------+
| SAF002                            | SAF016 | ACC ON 시 자가진단 (공유)                   | (상동)                                           |
+-----------------------------------+--------+---------------------------------------------+--------------------------------------------------+
| SAF003 (운전자 오버라이드 보장)   | SAF004 | 브레이크 시 모터 즉시 중지 (공유)           | (상동)                                           |
+-----------------------------------+--------+---------------------------------------------+--------------------------------------------------+
| SAF003                            | SAF015 | 액셀 시 STANDBY 전이                        | 10ms 주기 액셀 감시 + 즉시 STANDBY 전이          |
+-----------------------------------+--------+---------------------------------------------+--------------------------------------------------+
| SAF003                            | SAF017 | 페달 입력 중 활성화 방지 (공유)             | (상동)                                           |
+-----------------------------------+--------+---------------------------------------------+--------------------------------------------------+

하위 기술적 안전 메커니즘 (TSR):

+--------+-----------------------------------------------+-------------------------+
| TSR ID | 안전 메커니즘                                 | 대상                    |
+========+===============================================+=========================+
| SAF009 | 브레이크 신호 이중화 읽기 (Redundant sensing) | 브레이크 버튼 입력      |
+--------+-----------------------------------------------+-------------------------+
| SAF010 | E2E P01 (RC+CRC, 선택적 적용)                 | ECU_PWM_CMD(0x200)만    |
+--------+-----------------------------------------------+-------------------------+
| SAF011 | 워치독 타이머 (SW 행 감지)                    | 메인 ECU                |
+--------+-----------------------------------------------+-------------------------+
| SAF012 | 프로그램 흐름 모니터링 (실행 순서 감시)       | 10ms 제어 루프          |
+--------+-----------------------------------------------+-------------------------+
| SAF013 | RAM 무결성 테스트                             | 안전 관련 RAM 영역      |
+--------+-----------------------------------------------+-------------------------+
| SAF014 | 모터 구동 독립 차단 경로 (HW 안전 경로)       | 모터 드라이버 Enable 핀 |
+--------+-----------------------------------------------+-------------------------+

FSC 완전성 확인: 모든 Safety Goal이 최소 1개 FSR으로 분해 완료되었다. 모든 FSR에 구체적 안전 메커니즘이 정의되었으며, SYS 요구사항으로의 추적성이 확보되어 있다. Safe State는 모든 FAULT/오류 상황에서 모터 출력 0(자연 감속) 또는 STANDBY(운전자 직접 제어)로 정의되어 있다.
<<<
ASIL: >>>
B
<<<
CATEGORY: >>>
FSC
<<<
VERIFICATION: >>>
A
<<<
PRIORITY: >>>
필수
<<<
RELATIONS:
- TYPE: Parent
  VALUE: SYS005
- TYPE: Parent
  VALUE: SYS006
- TYPE: Parent
  VALUE: SYS007
- TYPE: Parent
  VALUE: SYS022
- TYPE: Parent
  VALUE: SYS025
- TYPE: Parent
  VALUE: SYS033

[[/SECTION]]

[[SECTION]]
TITLE: 요구사항 완전성 및 일관성 검토

[REQUIREMENT]
UID: SYS2-QA-001
TITLE: 완전성 검토 결과
STATEMENT: >>>
SYS.2 분석 과정에서 수행한 완전성 검토 결과:

1. 상위 추적성 완전성: 모든 SYS 요구사항이 최소 1개의 STK 요구사항을 Parent로 참조.
2. 하위 분해 완전성: 모든 SYS 요구사항이 SWR, HWR, SAF 중 최소 1개에서 참조됨.
3. Safety Goal 커버리지: 3개 Safety Goal 모두 FSR로 분해 완료.
4. ASIL 일관성: ASIL B 요구사항의 하위 요구사항에 ASIL B 이상 태깅.
5. 검증 방법 할당: 모든 SYS 요구사항에 T/A/I/R 중 최소 1개 할당.
6. AEB 범위 제외 명시: 관련 요구사항(SYS005, SYS022, SAF002, SAF005, SAF007)에 AEB 미포함 명시.

잔여 과제(Open Issues):
1. 안전거리 모델 파라미터(Time-gap 계수)의 1/10 스케일 최적화: 실차 튜닝 단계에서 확정
2. 저전압(배터리 부족) 감지 FAULT 전이 요구사항 추가 검토
3. CAN 메시지 ID 할당표: 상세 설계 단계에서 확정
4. PID 제어 파라미터(Kp, Ki, Kd): Simulink MBD 시뮬레이션 후 확정
5. E2E 보호(Rolling Counter + CRC, AUTOSAR Profile 01)는 액추에이터 직접 제어 경로인 MTR_CMD(ECU_PWM_CMD 0x200)에만 선택적 적용한다(SAF010). 센서 상향(SENSOR_FUSION 0x110, SENSOR_HEARTBEAT 0x111), 운전자 입력(SENSOR_ACC_CMD 0x100), HMI 표시(ECU_ACC_STATUS 0x400), 모터 피드백(MTR_SPD_FB 0x300) 경로는 3주기 연속 미수신 타임아웃(SYS025) 과 수신측 플러시블리티 검사로 무결성을 확보한다. 근거: (a) 단일 결함 지점 우선순위 — 액추에이터 직전 명령이 비트 반전되면 모터 오동작으로 즉시 연결되나, 상향 경로는 ECU 내부에서 추가 검증 가능, (b) 구현 범위 제약 — 모든 메시지에 E2E 적용 시 범위 과대, (c) ISO 26262 ASIL decomposition 관점에서 안전 메커니즘의 위험 기반 선택적 배치가 정당. DBC(acc_db.dbc) 에 E2E 시그널 추가 및 Arduino/ECU 측 CRC 구현은 후속 스프린트 과제.
<<<
ASIL: QM
CATEGORY: 분석
VERIFICATION: R
PRIORITY: 필수
RELATIONS:
- TYPE: Parent
  VALUE: SYS001

[REQUIREMENT]
UID: SYS2-QA-002
TITLE: 일관성 검토 결과
STATEMENT: >>>
요구사항 간 일관성 검토 결과:

1. 오버라이드 동작 일관성:
- 브레이크(SYS006): STANDBY 전이 + 설정값 보존
- 액셀(SYS007): STANDBY 전이 + 설정값 보존
- 두 오버라이드 동작이 동일한 패턴(-> STANDBY, 설정값 보존)으로 일관됨

2. FAULT 동작 일관성:
- SYS005, SYS025: 모터 출력 0 + HMI 경고 + ACC ON/OFF만 유효
- 능동 감속 없음(자연 감속) 정책이 모든 FAULT 시나리오에 일관 적용

3. 타이밍 일관성:
- 오버라이드 응답(50ms) < FTTI(100ms): 안전 마진 확보
- CAN 타임아웃(3주기) = 센서 60ms, 모터 30ms: 주기 대비 일관
- 제어 루프(10ms) < 센서 갱신(20~100ms): 제어 주기가 센서 주기보다 빨라 최신 데이터 반영 보장

4. 버튼 가용성 일관성:
- SYS029 버튼 매트릭스와 SYS002~005 상태별 유효 입력이 일치
- OFF: ACC ON/OFF만 유효
- STANDBY: SET, RES, 거리설정 유효
- CRUISING/FOLLOWING: 속도+/-, 거리설정, 일시정지 유효
- FAULT: ACC ON/OFF만 유효

발견된 불일관 사항: 없음
<<<
ASIL: QM
CATEGORY: 분석
VERIFICATION: R
PRIORITY: 필수
RELATIONS:
- TYPE: Parent
  VALUE: SYS001

[[/SECTION]]
