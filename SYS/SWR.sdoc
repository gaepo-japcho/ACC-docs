[DOCUMENT]
TITLE: ACC Software Requirements (SWR)

[GRAMMAR]
ELEMENTS:
- TAG: REQUIREMENT
  FIELDS:
  - TITLE: UID
    TYPE: String
    REQUIRED: True
  - TITLE: TITLE
    TYPE: String
    REQUIRED: False
  - TITLE: STATEMENT
    TYPE: String
    REQUIRED: True
  - TITLE: ASIL
    TYPE: String
    REQUIRED: False
  - TITLE: CATEGORY
    TYPE: String
    REQUIRED: False
  - TITLE: VERIFICATION
    TYPE: String
    REQUIRED: False
  - TITLE: SWC
    TYPE: String
    REQUIRED: False
  - TITLE: COMMENT
    TYPE: String
    REQUIRED: False
  RELATIONS:
  - TYPE: Parent

[[SECTION]]
TITLE: AccStateMachine

[REQUIREMENT]
UID: SWR001
TITLE: ACC 상태 머신 구현
STATEMENT: >>>
ACC StateMachine SWC는 OFF, STANDBY, CRUISING, FOLLOWING, FAULT 5개 상태를 관리한다.
OFF→CRUISING/FOLLOWING: ACC ON + 자가진단 통과 (현재 속도를 최고속도로 설정)
STANDBY→CRUISING/FOLLOWING: SET 또는 RES 버튼
CRUISING↔FOLLOWING: 전방 차량 감지/소멸
CRUISING/FOLLOWING→STANDBY: 브레이크, 액셀, 일시정지
Any Active→FAULT: 고장 감지
FAULT→OFF: ACC ON/OFF 토글
Any→OFF: ACC ON/OFF 토글
<<<
ASIL: B
CATEGORY: 기능
VERIFICATION: T
SWC: AccStateMachine
RELATIONS:
- TYPE: Parent
  VALUE: SYS001
- TYPE: Parent
  VALUE: SYS002
- TYPE: Parent
  VALUE: SYS003
- TYPE: Parent
  VALUE: SYS004
- TYPE: Parent
  VALUE: SYS005

[REQUIREMENT]
UID: SWR002
TITLE: 브레이크 오버라이드 처리 (→ STANDBY)
STATEMENT: >>>
브레이크 페달 신호가 Active이면 현재 상태와 무관하게 즉시 STANDBY 전이. 처리 지연 50ms 이내. 10ms 주기 태스크에서 브레이크 상태를 확인한다. STANDBY 전이 시 설정 속도 및 안전거리 단계 값을 내부 변수에 보존한다.
<<<
ASIL: B
CATEGORY: 안전
VERIFICATION: T
SWC: AccStateMachine
RELATIONS:
- TYPE: Parent
  VALUE: SYS006

[REQUIREMENT]
UID: SWR003
TITLE: 가속 오버라이드 처리 (→ STANDBY)
STATEMENT: >>>
액셀 페달 신호가 Active이면 현재 상태와 무관하게 즉시 STANDBY 전이. 이전 설정 속도와 안전거리 단계를 보존한다. 액셀 오버라이드 응답 시간은 50ms 이내.
<<<
ASIL: QM
CATEGORY: 기능
VERIFICATION: T
SWC: AccStateMachine
RELATIONS:
- TYPE: Parent
  VALUE: SYS007

[REQUIREMENT]
UID: SWR026
TITLE: SET/RES 버튼 처리
STATEMENT: >>>
STANDBY 상태에서:
- SET 버튼 수신 시: 현재 자차 속도를 최고속도로 설정, 전방 차량 유무에 따라 CRUISING/FOLLOWING 전이
- RES 버튼 수신 시: 보존된 이전 최고속도를 복원, 전방 차량 유무에 따라 CRUISING/FOLLOWING 전이
SET/RES는 STANDBY에서만 유효하며, 다른 상태에서 수신 시 무시한다.
<<<
ASIL: QM
CATEGORY: 기능
VERIFICATION: T
SWC: AccStateMachine
RELATIONS:
- TYPE: Parent
  VALUE: SYS027

[REQUIREMENT]
UID: SWR027
TITLE: 일시정지 버튼 처리
STATEMENT: >>>
CRUISING 또는 FOLLOWING 상태에서 일시정지 버튼 CAN 메시지 수신 시 STANDBY로 전이한다. 이전 설정 속도와 안전거리 단계를 보존한다. 일시정지 버튼은 CRUISING/FOLLOWING 상태에서만 유효하며, 다른 상태에서는 무시한다.
<<<
ASIL: QM
CATEGORY: 기능
VERIFICATION: T
SWC: AccStateMachine
RELATIONS:
- TYPE: Parent
  VALUE: SYS028

[REQUIREMENT]
UID: SWR028
TITLE: 버튼 가용성 상태 관리
STATEMENT: >>>
현재 ACC 상태에 따라 각 버튼의 활성/비활성 플래그를 관리한다. 비활성 버튼의 CAN 메시지가 수신되면 해당 입력을 무시한다. 버튼 가용성 정보를 HMI GUI로 CAN 전송하여 그레이아웃 표시에 활용한다.
<<<
ASIL: QM
CATEGORY: 기능
VERIFICATION: T
SWC: AccStateMachine
RELATIONS:
- TYPE: Parent
  VALUE: SYS029

[REQUIREMENT]
UID: SWR029
TITLE: ACC ON 자가진단
STATEMENT: >>>
ACC ON/OFF 토글 수신 시 (OFF→ON 방향), 다음 사전 조건 및 자가진단을 수행한다:
사전 조건 확인:
- 브레이크/액셀 페달 입력 확인 → 눌려있으면 활성화 거부 (OFF 유지)
자가진단:
- CAN 통신 상태 확인 (각 노드 정상 응답)
- 센서 데이터 유효성 확인 (LiDAR, 카메라, 인코더)
자가진단 통과 시 안전거리 단계를 기본값 3단계(원거리)로 초기화한다.
자가진단 실패 시 ACC를 켜지 않고 OFF 상태를 유지하며, HMI에 진단 실패 메시지를 표시한다.
<<<
ASIL: B
CATEGORY: 안전
VERIFICATION: T
SWC: AccStateMachine
RELATIONS:
- TYPE: Parent
  VALUE: SYS001
- TYPE: Parent
  VALUE: SYS005
- TYPE: Parent
  VALUE: SYS033
- TYPE: Parent
  VALUE: SYS034

[REQUIREMENT]
UID: SWR031
TITLE: 최소 설정 속도 클램핑
STATEMENT: >>>
ACC 활성화 시 설정 최고속도를 max(현재속도, 최소설정속도)로 클램핑한다. 최소설정속도는 캘리브레이션 파라미터로 정의하며, 1/10 스케일카 특성에 맞게 튜닝한다. 속도+/- 버튼으로 조정 시에도 최소설정속도 이하로 내려가지 않도록 제한한다.
<<<
ASIL: QM
CATEGORY: 기능
VERIFICATION: T
SWC: AccStateMachine
RELATIONS:
- TYPE: Parent
  VALUE: SYS032

[[/SECTION]]

[[SECTION]]
TITLE: SensorProcessing

[REQUIREMENT]
UID: SWR004
TITLE: LiDAR 거리 데이터 수신
STATEMENT: >>>
CAN RX로 수신된 LiDAR 거리값(16bit, mm 단위)을 내부 변수에 저장한다. 메시지 타임아웃(60ms 미수신) 시 센서 이상 플래그를 설정한다.
<<<
ASIL: B
CATEGORY: 기능
VERIFICATION: T
SWC: SensorProcessing
RELATIONS:
- TYPE: Parent
  VALUE: SYS015
- TYPE: Parent
  VALUE: SYS025

[REQUIREMENT]
UID: SWR005
TITLE: 전방 차량 감지 상태 처리
STATEMENT: >>>
CAN RX로 수신된 전방 차량 감지 플래그(1bit)를 처리한다. 감지 → 미감지 전환 시 디바운싱(예: 3연속 미감지)을 적용하여 오인식을 방지한다.
<<<
ASIL: QM
CATEGORY: 기능
VERIFICATION: T
SWC: SensorProcessing
RELATIONS:
- TYPE: Parent
  VALUE: SYS011
- TYPE: Parent
  VALUE: SYS015

[REQUIREMENT]
UID: SWR006
TITLE: 상대속도 데이터 처리
STATEMENT: >>>
CAN RX로 수신된 전방 차량 상대속도(16bit, 0.01m/s)를 처리한다. 이동평균 필터(윈도우 5샘플)를 적용하여 노이즈를 저감한다.
<<<
ASIL: QM
CATEGORY: 기능
VERIFICATION: T
SWC: SensorProcessing
RELATIONS:
- TYPE: Parent
  VALUE: SYS013
- TYPE: Parent
  VALUE: SYS015

[REQUIREMENT]
UID: SWR007
TITLE: 자차 속도 수신 및 처리
STATEMENT: >>>
모터 제어기(STM32)에서 CAN RX로 수신된 인코더 기반 속도값을 처리한다. 타임아웃 시 속도 이상 플래그를 설정한다.
<<<
ASIL: QM
CATEGORY: 기능
VERIFICATION: T
SWC: SensorProcessing
RELATIONS:
- TYPE: Parent
  VALUE: SYS012
- TYPE: Parent
  VALUE: SYS017

[[/SECTION]]

[[SECTION]]
TITLE: DistanceControl

[REQUIREMENT]
UID: SWR008
TITLE: 안전거리 목표값 계산 (AEB 미포함)
STATEMENT: >>>
현재 선택된 안전거리 단계(1~3)와 자차 속도를 기반으로 목표 차간거리를 계산한다. 단계별 Time-gap 계수: 1단계=0.8s, 2단계=1.2s, 3단계=1.6s. 목표 거리 이하 접근 시 PID 제어 범위 내에서 최대 감속을 수행한다. 비상 제동(AEB)은 수행하지 않는다.
<<<
ASIL: B
CATEGORY: 기능
VERIFICATION: T
SWC: DistanceControl
RELATIONS:
- TYPE: Parent
  VALUE: SYS008
- TYPE: Parent
  VALUE: SYS009
- TYPE: Parent
  VALUE: SYS010
- TYPE: Parent
  VALUE: SYS022

[REQUIREMENT]
UID: SWR009
TITLE: PID 제어기 구현
STATEMENT: >>>
Simulink MBD에서 생성된 PID 제어 코드를 실행한다. 입력: 목표 거리/속도와 실측값의 오차. 출력: 모터 제어 명령. 제어 주기: 10ms. Anti-windup 기능을 포함한다.
<<<
ASIL: QM
CATEGORY: 기능
VERIFICATION: T
SWC: DistanceControl
RELATIONS:
- TYPE: Parent
  VALUE: SYS014
- TYPE: Parent
  VALUE: SYS024

[REQUIREMENT]
UID: SWR010
TITLE: CRUISE 모드 속도 제어
STATEMENT: >>>
CRUISE 상태에서 설정 속도를 목표로 PID 속도 제어를 수행한다. 전방 차량 감지 시 FOLLOWING 전환 트리거를 StateMachine에 전달한다.
<<<
ASIL: QM
CATEGORY: 기능
VERIFICATION: T
SWC: DistanceControl
RELATIONS:
- TYPE: Parent
  VALUE: SYS003
- TYPE: Parent
  VALUE: SYS014

[REQUIREMENT]
UID: SWR011
TITLE: FOLLOWING 모드 거리 제어
STATEMENT: >>>
FOLLOWING 상태에서 목표 차간거리를 유지하도록 PID 거리 제어를 수행한다. 전방 차량 소멸 시 CRUISE 전환 트리거를 StateMachine에 전달한다.
<<<
ASIL: B
CATEGORY: 기능
VERIFICATION: T
SWC: DistanceControl
RELATIONS:
- TYPE: Parent
  VALUE: SYS004
- TYPE: Parent
  VALUE: SYS014

[[/SECTION]]

[[SECTION]]
TITLE: CanCommunication

[REQUIREMENT]
UID: SWR012
TITLE: CAN TX - 모터 제어 명령 송신
STATEMENT: >>>
메인 ECU(MPC5606B)에서 모터 제어기(STM32)로 목표 모터 PWM/속도 명령을 CAN 전송한다. 메시지 주기: 10ms. DLC: 8 bytes.
<<<
ASIL: QM
CATEGORY: 인터페이스
VERIFICATION: T
SWC: CanCommunication
RELATIONS:
- TYPE: Parent
  VALUE: SYS016

[REQUIREMENT]
UID: SWR013
TITLE: CAN RX - 센서 데이터 수신
STATEMENT: >>>
카메라+LiDAR 처리 유닛으로부터 전방 차량 정보(감지 여부, 거리, 상대속도) CAN 메시지를 수신한다. 수신 주기: 20ms. 타임아웃: 60ms.
<<<
ASIL: QM
CATEGORY: 인터페이스
VERIFICATION: T
SWC: CanCommunication
RELATIONS:
- TYPE: Parent
  VALUE: SYS015

[REQUIREMENT]
UID: SWR014
TITLE: CAN RX - 모터 피드백 수신
STATEMENT: >>>
모터 제어기(STM32)로부터 실측 속도, 모터 상태 CAN 메시지를 수신한다. 수신 주기: 10ms. 타임아웃: 30ms.
<<<
ASIL: QM
CATEGORY: 인터페이스
VERIFICATION: T
SWC: CanCommunication
RELATIONS:
- TYPE: Parent
  VALUE: SYS017

[REQUIREMENT]
UID: SWR015
TITLE: CAN 메시지 타임아웃 감시
STATEMENT: >>>
각 CAN RX 메시지에 대해 타임아웃 카운터를 관리한다. 타임아웃 발생 시 해당 데이터를 무효화하고 Diagnostics SWC에 에러를 보고한다.
<<<
ASIL: B
CATEGORY: 안전
VERIFICATION: T
SWC: CanCommunication
RELATIONS:
- TYPE: Parent
  VALUE: SYS025

[[/SECTION]]

[[SECTION]]
TITLE: Diagnostics

[REQUIREMENT]
UID: SWR016
TITLE: 고장 감지 및 FAULT 전이 (능동 감속 없음)
STATEMENT: >>>
센서 이상, CAN 타임아웃, 제어 이상 등을 감지하면 StateMachine에 FAULT 전이를 요청한다. FAULT 진입 시 모터 제어 출력을 0으로 설정한다 (능동 감속 없음). HMI에 FAULT 경고를 즉시 전달한다. FAULT 상태에서는 ACC ON/OFF 토글만 처리하며(→ OFF), 그 외 입력은 무시한다.
<<<
ASIL: B
CATEGORY: 안전
VERIFICATION: T
SWC: Diagnostics
RELATIONS:
- TYPE: Parent
  VALUE: SYS005
- TYPE: Parent
  VALUE: SYS025

[REQUIREMENT]
UID: SWR017
TITLE: DTC(Diagnostic Trouble Code) 관리
STATEMENT: >>>
고장 발생 시 DTC를 저장한다. DTC는 고장 유형, 발생 시각, 발생 횟수를 포함한다.
<<<
ASIL: QM
CATEGORY: 기능
VERIFICATION: T
SWC: Diagnostics
RELATIONS:
- TYPE: Parent
  VALUE: SYS005

[[/SECTION]]

[[SECTION]]
TITLE: HmiManager

[REQUIREMENT]
UID: SWR018
TITLE: HMI GUI 표시 (클러스터)
STATEMENT: >>>
RPi/Jetson에서 실행되는 GUI 애플리케이션을 통해 현재 ACC 상태, 설정 속도, 안전거리 단계, 전방 차량 감지, 자차 속도를 표시한다. 메인 ECU로부터 CAN 수신한 데이터를 GUI에 반영한다. 갱신 주기: 50ms.
상태별 버튼 그레이아웃 처리를 수행한다.
<<<
ASIL: QM
CATEGORY: 기능
VERIFICATION: I
SWC: HmiManager
RELATIONS:
- TYPE: Parent
  VALUE: SYS019

[REQUIREMENT]
UID: SWR019
TITLE: FAULT 경고 표시
STATEMENT: >>>
FAULT 상태 진입 시 GUI에 경고 메시지를 즉시 표시한다. 경고는 운전자가 ACC ON/OFF를 눌러 OFF 전이 시 해제된다. 시간 여유 시 경고음(buzzer 또는 SW audio)을 추가한다.
<<<
ASIL: QM
CATEGORY: 안전
VERIFICATION: T
SWC: HmiManager
RELATIONS:
- TYPE: Parent
  VALUE: SYS005
- TYPE: Parent
  VALUE: SYS019

[[/SECTION]]

[[SECTION]]
TITLE: DriverInput

[REQUIREMENT]
UID: SWR020
TITLE: 운전자 입력 처리 (GUI → CAN)
STATEMENT: >>>
GUI 가상 버튼 클릭 이벤트를 CAN 메시지로 변환하여 메인 ECU에 전송한다. 브레이크/액셀 페달 신호는 GPIO 또는 ADC 입력을 GUI와 별도로 CAN 전송할 수 있다. 버튼 입력에 대해 20ms 디바운싱을 적용한다 (GUI 클릭은 단일 이벤트이므로 반복 방지 용도). 브레이크/액셀 페달은 디바운싱 없이 즉시 처리한다.
<<<
ASIL: QM
CATEGORY: 기능
VERIFICATION: T
SWC: DriverInput
RELATIONS:
- TYPE: Parent
  VALUE: SYS018
- TYPE: Parent
  VALUE: SYS030

[[/SECTION]]

[[SECTION]]
TITLE: AUTOSAR OS 태스크

[REQUIREMENT]
UID: SWR021
TITLE: 태스크 주기 - 10ms
STATEMENT: >>>
제어 루프(PID 계산, 모터 명령 출력, 브레이크/액셀 감시)는 10ms 주기 태스크에서 수행한다.
<<<
ASIL: B
CATEGORY: 타이밍
VERIFICATION: T
SWC: AUTOSAR_OS
RELATIONS:
- TYPE: Parent
  VALUE: SYS014
- TYPE: Parent
  VALUE: SYS020

[REQUIREMENT]
UID: SWR022
TITLE: 태스크 주기 - 20ms
STATEMENT: >>>
센서 데이터 수신 처리(LiDAR, 카메라 융합 결과)는 20ms 주기 태스크에서 수행한다.
<<<
ASIL: QM
CATEGORY: 타이밍
VERIFICATION: T
SWC: AUTOSAR_OS
RELATIONS:
- TYPE: Parent
  VALUE: SYS021

[REQUIREMENT]
UID: SWR023
TITLE: 태스크 주기 - 100ms
STATEMENT: >>>
HMI 갱신, DTC 로깅, 진단 처리는 100ms 주기 태스크에서 수행한다.
<<<
ASIL: QM
CATEGORY: 타이밍
VERIFICATION: T
SWC: AUTOSAR_OS
RELATIONS:
- TYPE: Parent
  VALUE: SYS019

[[/SECTION]]

[[SECTION]]
TITLE: 코드 품질 및 아키텍처

[REQUIREMENT]
UID: SWR024
TITLE: MISRA-C:2012 준수
STATEMENT: >>>
모든 수동 작성 C 코드는 MISRA-C:2012 규칙을 준수한다. Mandatory/Required 규칙 위반 0건을 목표로 한다. Advisory는 편차 기록 후 허용.
<<<
ASIL: B
CATEGORY: 비기능
VERIFICATION: A
SWC: All
RELATIONS:
- TYPE: Parent
  VALUE: SYS023

[REQUIREMENT]
UID: SWR025
TITLE: AUTOSAR RTE 포트 정의
STATEMENT: >>>
각 SWC 간 데이터 교환은 AUTOSAR RTE Sender-Receiver 또는 Client-Server 포트를 통해 수행한다. mobilgene으로 AUTOSAR 설정 및 RTE 코드를 생성한다.
<<<
ASIL: QM
CATEGORY: 비기능
VERIFICATION: I
SWC: All
RELATIONS:
- TYPE: Parent
  VALUE: SYS023

[[/SECTION]]

[[SECTION]]
TITLE: GuiCanInterface

[REQUIREMENT]
UID: SWR030
TITLE: GUI-CAN 인터페이스 (RPi/Jetson측)
STATEMENT: >>>
RPi/Jetson에서 실행되는 GUI 애플리케이션은:
- 운전자 버튼 클릭 → CAN TX 메시지 생성 (20ms 주기)
- 메인 ECU로부터 CAN RX 메시지 수신 → GUI 화면 갱신 (50ms 주기)
- 카메라+LiDAR 처리 결과(전방 차량 정보)를 동일 CAN 버스로 전송
CAN 인터페이스는 USB-CAN 어댑터 또는 MCP2515 SPI-CAN 모듈을 사용한다.
<<<
ASIL: QM
CATEGORY: 인터페이스
VERIFICATION: T
SWC: GuiCanInterface
RELATIONS:
- TYPE: Parent
  VALUE: SYS015
- TYPE: Parent
  VALUE: SYS030
- TYPE: Parent
  VALUE: SYS031

[[/SECTION]]
