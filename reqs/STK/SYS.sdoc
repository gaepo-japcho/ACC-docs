[DOCUMENT]
TITLE: ACC System Requirements (SYS)

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: TITLE
    TYPE: String
    REQUIRED: False
  - TITLE: STATEMENT
    TYPE: String
    REQUIRED: True
  - TITLE: ASIL
    TYPE: String
    REQUIRED: False
  - TITLE: CATEGORY
    TYPE: String
    REQUIRED: False
  - TITLE: VERIFICATION
    TYPE: String
    REQUIRED: False
  - TITLE: COMMENT
    TYPE: String
    REQUIRED: False
  RELATIONS:
  - TYPE: Parent

[[SECTION]]
TITLE: 상태 전이

[REQUIREMENT]
UID: SYS001
TITLE: ACC 상태 전이 - OFF
STATEMENT: >>>
OFF 상태: ACC 기능 비활성. 운전자가 ACC ON/OFF 토글 버튼을 누르면:

- 브레이크 버튼 또는 액셀 페달이 눌려있는 경우: ACC 활성화 거부, OFF 유지
- 자가진단 실패(FAULT 조건) 시: ACC가 켜지지 않고 OFF 유지
- 자가진단 통과 + 전방 차량 미감지: 현재 속도를 최고속도로 설정, 안전거리 단계 3단계로 초기화, CRUISING으로 전이
- 자가진단 통과 + 전방 차량 감지: 현재 속도를 최고속도로 설정, 안전거리 단계 3단계로 초기화, FOLLOWING으로 전이
<<<
ASIL: >>>
QM
<<<
CATEGORY: >>>
기능
<<<
VERIFICATION: >>>
T
<<<
RELATIONS:
- TYPE: Parent
  VALUE: STK009
- TYPE: Parent
  VALUE: STK022

[REQUIREMENT]
UID: SYS002
TITLE: ACC 상태 전이 - STANDBY
STATEMENT: >>>
STANDBY 상태: ACC 활성화 대기 (브레이크, 액셀, 일시정지에 의해 진입).
이전 설정 속도와 안전거리 단계를 보존한다.

- SET 버튼: 현재 주행 속도를 최고속도로 설정, 전방 차량 유무에 따라 CRUISING 또는 FOLLOWING 전이
- RES 버튼: 보존된 이전 설정 속도를 최고속도로 복원, 전방 차량 유무에 따라 CRUISING 또는 FOLLOWING 전이
- ACC ON/OFF 토글: OFF로 전이

STANDBY에서 속도+/-, 일시정지 버튼은 비활성(무시).
<<<
ASIL: >>>
QM
<<<
CATEGORY: >>>
기능
<<<
VERIFICATION: >>>
T
<<<
RELATIONS:
- TYPE: Parent
  VALUE: STK009

[REQUIREMENT]
UID: SYS003
TITLE: ACC 상태 전이 - CRUISING
STATEMENT: >>>
CRUISING 상태: 전방 차량 미감지 시 설정된 최고속도를 유지하며 주행.

- 전방 차량이 안전거리 이내에 감지: FOLLOWING으로 전이
- 브레이크 입력: STANDBY로 전이
- 액셀 입력: STANDBY로 전이
- 일시정지 버튼: STANDBY로 전이
- 속도+/- 버튼: 설정 최고속도 조정 (CRUISING 유지)
- 거리설정 버튼: 안전거리 단계 변경 (CRUISING 유지)
- 고장 감지: FAULT로 전이
- ACC ON/OFF 토글: OFF로 전이

CRUISING에서 SET/RES 버튼은 비활성(무시).
<<<
ASIL: >>>
QM
<<<
CATEGORY: >>>
기능
<<<
VERIFICATION: >>>
T
<<<
RELATIONS:
- TYPE: Parent
  VALUE: STK005
- TYPE: Parent
  VALUE: STK009

[REQUIREMENT]
UID: SYS004
TITLE: ACC 상태 전이 - FOLLOWING
STATEMENT: >>>
FOLLOWING 상태: 전방 차량 추종. 설정된 안전거리 단계에 따른 목표 차간거리를 유지하도록 속도 제어.
자차 속도는 설정 최고속도를 초과하지 않는다.

- 전방 차량 소멸: CRUISING으로 전이
- 브레이크 입력: STANDBY로 전이
- 액셀 입력: STANDBY로 전이
- 일시정지 버튼: STANDBY로 전이
- 속도+/- 버튼: 설정 최고속도 조정 (FOLLOWING 유지)
- 거리설정 버튼: 안전거리 단계 변경 (FOLLOWING 유지)
- 고장 감지: FAULT로 전이
- ACC ON/OFF 토글: OFF로 전이

FOLLOWING에서 SET/RES 버튼은 비활성(무시).
<<<
ASIL: B
CATEGORY: 기능
VERIFICATION: T
RELATIONS:
- TYPE: Parent
  VALUE: STK004
- TYPE: Parent
  VALUE: STK006
- TYPE: Parent
  VALUE: STK009

[REQUIREMENT]
UID: SYS005
TITLE: ACC 상태 전이 - FAULT
STATEMENT: >>>
FAULT 상태: 센서 고장, CAN 통신 단절 등 감지 시 진입.

- 모터 제어 출력을 0으로 설정 (능동 감속 없음, 자연 감속)
- HMI에 FAULT 경고를 즉시 표시 (시간 여유 시 경고음 추가)
- 운전자가 ACC ON/OFF 토글 버튼을 눌러야 OFF로 전이
- FAULT에서 ACC ON/OFF 외의 모든 버튼은 비활성(무시)
- 운전자는 FAULT 발생 시 즉시 직접 개입하여 차량을 제어해야 한다

ACC OFF 상태에서 자가진단 실패 시 ACC를 켤 수 없다 (FAULT 상태로 시작 불가).
<<<
ASIL: B
CATEGORY: 안전
VERIFICATION: T
RELATIONS:
- TYPE: Parent
  VALUE: STK009
- TYPE: Parent
  VALUE: STK010
- TYPE: Parent
  VALUE: STK022

[[/SECTION]]

[[SECTION]]
TITLE: 운전자 오버라이드

[REQUIREMENT]
UID: SYS006
TITLE: 브레이크 오버라이드 (→ STANDBY)
STATEMENT: >>>
브레이크 버튼 입력 감지 시, 현재 상태와 무관하게 ACC를 즉시 STANDBY 상태로 전이한다. 브레이크 버튼은 디지털 입력(ON/OFF)이며, 눌려있는 동안 지속적으로 제동 상태로 간주한다 (CAN 시그널: BTN_BRAKE, 1bit). 브레이크 오버라이드 응답 시간은 50ms 이내여야 한다. STANDBY 전이 시 설정 속도 및 안전거리 단계 값을 보존한다.
<<<
ASIL: B
CATEGORY: 안전
VERIFICATION: T
RELATIONS:
- TYPE: Parent
  VALUE: STK007

[REQUIREMENT]
UID: SYS007
TITLE: 가속 오버라이드 (→ STANDBY)
STATEMENT: >>>
액셀 입력 감지 시, ACC를 즉시 STANDBY 상태로 전이한다. 이전 설정 속도와 안전거리 단계를 보존한다. 액셀 오버라이드 응답 시간은 50ms 이내여야 한다.
<<<
ASIL: QM
CATEGORY: 기능
VERIFICATION: T
RELATIONS:
- TYPE: Parent
  VALUE: STK008

[[/SECTION]]

[[SECTION]]
TITLE: 안전거리 모델

[REQUIREMENT]
UID: SYS008
TITLE: 안전거리 모델 - 단계 1
STATEMENT: >>>
안전거리 1단계(근거리): 목표 차간거리 = 최소 안전거리 + 0.8초 * 자차속도에 해당하는 거리. (1/10 스케일 기준 파라미터 튜닝 필요)
<<<
ASIL: >>>
QM
<<<
CATEGORY: >>>
기능
<<<
VERIFICATION: >>>
T
<<<
RELATIONS:
- TYPE: Parent
  VALUE: STK006

[REQUIREMENT]
UID: SYS009
TITLE: 안전거리 모델 - 단계 2
STATEMENT: >>>
안전거리 2단계(중거리): 목표 차간거리 = 최소 안전거리 + 1.2초 * 자차속도에 해당하는 거리. (1/10 스케일 기준 파라미터 튜닝 필요)
<<<
ASIL: >>>
QM
<<<
CATEGORY: >>>
기능
<<<
VERIFICATION: >>>
T
<<<
RELATIONS:
- TYPE: Parent
  VALUE: STK006

[REQUIREMENT]
UID: SYS010
TITLE: 안전거리 모델 - 단계 3
STATEMENT: >>>
안전거리 3단계(원거리): 목표 차간거리 = 최소 안전거리 + 1.6초 * 자차속도에 해당하는 거리. (1/10 스케일 기준 파라미터 튜닝 필요)
<<<
ASIL: >>>
QM
<<<
CATEGORY: >>>
기능
<<<
VERIFICATION: >>>
T
<<<
RELATIONS:
- TYPE: Parent
  VALUE: STK006

[REQUIREMENT]
UID: SYS035
TITLE: 안전거리 모델 - 최소 안전거리
STATEMENT: >>>
최소 안전거리는 10cm로 정한다.
이는 목표속도가 제일 낮은 5cm/s에서 2초의 안전 시간을 확보하기 위함이다.
<<<
ASIL: >>>
QM
<<<
CATEGORY: >>>
기능
<<<
VERIFICATION: >>>
T
<<<
RELATIONS:
- TYPE: Parent
  VALUE: STK006

[[/SECTION]]

[[SECTION]]
TITLE: 인식 및 측정

[REQUIREMENT]
UID: SYS011
TITLE: 전방 차량 인식 처리
STATEMENT: >>>
카메라 기반 전방 차량 인식 시스템은 Raspberry Pi에서 실행된다. 인식 결과(차량 유무)와 LiDAR 거리 데이터를 융합하여 전방 차량 존재 여부 및 거리를 확정한다.
<<<
ASIL: QM
CATEGORY: 기능
VERIFICATION: T
RELATIONS:
- TYPE: Parent
  VALUE: STK002
- TYPE: Parent
  VALUE: STK003

[REQUIREMENT]
UID: SYS012
TITLE: 자차 속도 측정
STATEMENT: >>>
인코더 모터의 펄스 카운트를 기반으로 자차 속도를 계산한다. 속도 측정 주기는 10ms 이하, 속도 분해능은 1cm/s 이상이어야 한다.
<<<
ASIL: QM
CATEGORY: 성능
VERIFICATION: T
RELATIONS:
- TYPE: Parent
  VALUE: STK016

[REQUIREMENT]
UID: SYS013
TITLE: 전방 차량 상대속도 산출
STATEMENT: >>>
메인 ECU(MPC5606B)는 CAN으로 수신한 차간거리(VEH_DIST)의 시간 미분과 자차 속도(인코더 기반)를 조합하여 전방 차량의 상대속도를 내부적으로 산출한다. 산출된 상대속도는 ECU 내부 제어 로직(거리/속도 PID)에서만 사용되며 CAN 버스로 재전송되지 않는다. RPi 및 Arduino는 센서 I/O만 담당하고 상대속도 연산은 수행하지 않는다.
<<<
ASIL: QM
CATEGORY: 기능
VERIFICATION: T
RELATIONS:
- TYPE: Parent
  VALUE: STK012
- TYPE: Parent
  VALUE: STK017

[[/SECTION]]

[[SECTION]]
TITLE: 제어 및 성능

[REQUIREMENT]
UID: SYS014
TITLE: PID 속도/거리 제어 (cascaded)
STATEMENT: >>>
Simulink MBD로 설계된 cascaded 제어기를 통해 목표 속도/거리를 추종한다. 정상 상태 오차는 목표 속도의 5% 이내여야 한다.

cascaded 구조:

- **바깥 루프 (20ms, DistanceControl SWC)**: 거리 PID — FwdDistance 와 SafeDistance 의 오차로부터 목표 속도 TargetSpeedCmS 산출. CRUISING 모드에서는 TargetSpeedCmS = SetSpeedCmS 로 직접 전달 (PID 비활성).
- **안쪽 루프 (10ms, MotorControl SWC)**: 속도 PI — TargetSpeedCmS 와 실제 속도 EgoSpeedCmS(MTR_SPD_FB.GET_SPD_AVG) 의 오차로부터 PWM duty 산출. FF Lookup + PI, SAF008 클램핑 포함.

두 루프 주기 비율 2× 로 대역폭 분리 — cascaded 안정성 마진 확보. SENSOR_FUSION 수신 주기(20ms, SYS015) 와 바깥 루프 주기 일치.
<<<
ASIL: QM
CATEGORY: 성능
VERIFICATION: T
RELATIONS:
- TYPE: Parent
  VALUE: STK004

[REQUIREMENT]
UID: SYS020
TITLE: 제어 응답 시간
STATEMENT: >>>
전방 차량 감지에서 제어 명령 출력까지의 종단간 지연은 100ms 이내여야 한다.
<<<
ASIL: B
CATEGORY: 성능
VERIFICATION: T
RELATIONS:
- TYPE: Parent
  VALUE: STK004

[REQUIREMENT]
UID: SYS021
TITLE: 센서 데이터 갱신 주기
STATEMENT: >>>
LiDAR 거리 데이터 갱신 주기: 50ms 이하. 카메라 차량 인식 주기: 100ms 이하.
<<<
ASIL: QM
CATEGORY: 성능
VERIFICATION: T
RELATIONS:
- TYPE: Parent
  VALUE: STK002
- TYPE: Parent
  VALUE: STK003

[REQUIREMENT]
UID: SYS022
TITLE: 차간거리 접근 시 제어 (AEB 미포함)
STATEMENT: >>>
FOLLOWING 모드에서 차간거리가 목표 거리 이하로 감소하면 PID 제어 범위 내에서 최대 감속을 수행한다. 본 시스템은 AEB를 포함하지 않으므로 비상 제동(긴급 정지)은 수행하지 않는다. 위험 상황에서의 제동은 운전자의 직접 개입에 의한다.
<<<
ASIL: B
CATEGORY: 안전
VERIFICATION: T
RELATIONS:
- TYPE: Parent
  VALUE: STK004
- TYPE: Parent
  VALUE: STK023

[[/SECTION]]

[[SECTION]]
TITLE: CAN 통신

[REQUIREMENT]
UID: SYS015
TITLE: CAN 통신 - 센서 → 메인 ECU
STATEMENT: >>>
카메라+LiDAR 처리 유닛(RPi)은 CAN 메시지 SENSOR_FUSION(0x110)로 다음 정보를 메인 ECU(MPC5606B)에 전송한다: 전방 차량 감지 여부 VEH_DET(1bit), 차간거리 VEH_DIST(16bit, mm, 0~12000). 전송 주기: 20ms, DLC: 3 Byte. 상대속도는 메인 ECU에서 내부 산출한다(SYS013 참조).
<<<
ASIL: QM
CATEGORY: 인터페이스
VERIFICATION: T
RELATIONS:
- TYPE: Parent
  VALUE: STK012

[REQUIREMENT]
UID: SYS016
TITLE: CAN 통신 - 메인 ECU → 모터 제어기
STATEMENT: >>>
MotorControl SWC가 산출한 목표 PWM duty(TargetPwmDuty)를 CanCommunication SWC가 CAN 메시지 MTR_CMD(0x210)로 Arduino 모터 제어 보드에 전송한다. DLC: 6 byte (PWM 4ch × 1byte + MTR_RC 4bit + MTR_CRC 8bit).

MotorControl SWC 제어 분기 (SWR032/033/034):

- ACC 활성(CRUISING/FOLLOWING): inner-loop 속도 PI (SWR034) — TargetSpeedCmS 와 EgoSpeedCmS(MTR_SPD_FB.GET_SPD_AVG) 오차로 PWM 산출, SAF008 클램핑
- STANDBY 수동 제어: GUI SET_ACCEL_PWM을 직접 PWM으로 출력 (PI 적분기 리셋)
- OFF/FAULT: TargetPwmDuty = 0, CmdValid = false (PI 적분기 리셋)

전송 주기: 10ms.

안전 메커니즘: 본 메시지는 액추에이터 직접 제어 경로이므로 AUTOSAR E2E Profile 01(Rolling Counter 4bit + CRC-8) 을 적용한다 (SAF010 참조). 수신 측 Arduino는 CRC/카운터 검증 실패 시 해당 명령을 무효 처리하고 30ms 타임아웃 규정(SWR018)에 따라 모터 출력 0으로 진입한다.
<<<
ASIL: B
CATEGORY: 인터페이스
VERIFICATION: T
RELATIONS:
- TYPE: Parent
  VALUE: STK012
- TYPE: Parent
  VALUE: STK013

[REQUIREMENT]
UID: SYS017
TITLE: CAN 통신 - 모터 제어기 → 메인 ECU
STATEMENT: >>>
Arduino 모터 제어 보드는 속도 피드백을 단일 프레임 MTR_SPD_FB(0x300, DLC 8, 주기 10ms)로 송신한다. 프레임은 대표 속도(HMI 표시 + 제어 입력 겸용)와 4륜 개별 속도(로깅/확장용)를 함께 담으며, 수신자는 시그널별로 분리된다:

- **GET_SPD_AVG** (int16 × 0.02 cm/s, Byte 0-1): 수신자 ECU, SENSOR. **대표 차속** — ECU MotorControl SWC 의 inner-loop 속도 PI 입력 (SWR034, IF_SensorData.EgoSpeedCmS) + RPi HMI 계기판 표시 (SYS019). MTR 노드가 자체 엔코더로부터 산출 (현 하드웨어는 엔코더 1개 broadcast, 다중 엔코더 확장 시 MTR 쪽에서 평균 연산).
- **GET_SPD_LF/RF/LR/RR** (int12 × 0.3 cm/s, Byte 2-7): 수신자 ECU. **현재 미사용** — 4륜 개별 제어 확장 또는 로깅/디버그용 예약. DLC 8 포화 우회를 위해 int16 → int12 로 축소 (SYS012 분해능 1 cm/s 요건 충족).

차속 데이터 원천은 MTR 한 군데로 일원화 — ECU 는 ACC 상태 피드백(ACC_STATUS) 에 차속을 포함시키지 않는다. 모터 노드 생존/에러는 별도 MTR_HEARTBEAT(0x310, DLC 2, 10ms)로 송신한다.
<<<
ASIL: QM
CATEGORY: 인터페이스
VERIFICATION: T
RELATIONS:
- TYPE: Parent
  VALUE: STK012
- TYPE: Parent
  VALUE: STK016

[REQUIREMENT]
UID: SYS025
TITLE: CAN 통신 고장 감지 (→ FAULT)
STATEMENT: >>>
CAN 메시지 타임아웃(3주기 연속 미수신) 시 해당 노드 통신 이상으로 판단하고 FAULT 상태로 전이한다. 각 노드는 Heartbeat 및 에러코드를 CAN 메시지로 전송한다:

- RASPI: HB_SENSOR / ERR_SENSOR (SENSOR_HEARTBEAT, 0x111, 20ms 주기 → 60ms 타임아웃)
- MTR: HB_MTR / ERR_MTR (MTR_HEARTBEAT, 0x310, 10ms 주기 → 30ms 타임아웃) — CAN 게이트웨이 Arduino가 I2C로 연결된 모터 노드의 상태를 대신 송신한다
- ECU: HB_ECU / ERR_ECU (ECU_HEARTBEAT, 0x410, 10ms 주기 → 30ms 타임아웃, ASIL-B per SAF018)

ERR 시그널 값이 0이 아닌 경우 해당 노드의 고장으로 판단한다. FAULT 전이 시 모터 출력을 0으로 설정하고 HMI에 경고를 표시한다. 능동 감속은 수행하지 않는다.
<<<
ASIL: B
CATEGORY: 안전
VERIFICATION: T
RELATIONS:
- TYPE: Parent
  VALUE: STK010
- TYPE: Parent
  VALUE: STK012

[REQUIREMENT]
UID: SYS030
TITLE: CAN 통신 - GUI → 메인 ECU (운전자 입력)
STATEMENT: >>>
RPi GUI 애플리케이션은 운전자 입력을 기능 도메인별 두 CAN 메시지로 분리하여 메인 ECU(MPC5606B)에 전송한다.

**VEH_CTRL(0x120)** — 차량 직접 조작(브레이크/수동 액셀). 안전 critical (SAF004/015 ASIL-B, 50ms 응답 요건) 때문에 고우선 저번호 ID + 20ms 주기로 운용. DLC: 2 Byte.

- SET_ACCEL_PWM (int8, Byte 0, -128~127): PyQt GUI 슬라이더에서 직접 설정하는 수동 액셀 duty값. 음수는 후진 PWM(확장 옵션). STANDBY 상태에서 MotorControl SWC가 직접 PWM 출력에 사용한다 (SYS037, SWR033).
- BTN_BRAKE (1bit, Byte 1 [0]): 브레이크 버튼. 디지털 ON/OFF, 눌림 유지 시 지속 제동(level trigger).

**ACC_CTRL(0x510)** — ACC feature 버튼 + 설정값. DLC: 4 Byte. 전송 주기 50ms.

- BTN_ACC_OFF (1bit, Byte 0 [0]): ACC ON/OFF 토글 (엣지 트리거).
- BTN_ACC_SET (1bit, Byte 0 [1]): SET 버튼 (엣지 트리거, STANDBY 에서만 유효).
- BTN_ACC_RES (1bit, Byte 0 [2]): RES 버튼 (엣지 트리거, STANDBY 에서만 유효).
- BTN_ACC_CANCEL (1bit, Byte 0 [3]): 일시정지 버튼 (엣지 트리거, CRUISING/FOLLOWING 에서만 유효).
- SET_ACC_SPD (int16, Byte 1-2, -500~500 cm/s): 목표 최고속도 절대값. 속도+/- 조정은 GUI 가 현재 설정값 ± 증분 계산해 절대값으로 전송. 하한 클램프는 수신측 ECU(SWR031, 최소 5 cm/s)에서 수행.
- SET_ACC_LVL (uint8, Byte 3): 거리 단계 절대값 (1=CLOSE, 2=MEDIUM, 3=FAR). 거리 버튼 클릭 시 해당 단계 값 전송.

분할 근거: 브레이크/액셀 오버라이드는 SAF004/SAF015 ASIL-B, 50ms 응답 요건이라 20ms 고속 주기 필요. ACC 버튼은 300ms 디바운싱·엣지 트리거라 50ms 주기로 충분하며, 안전 path 와 feature path 를 분리해 혼재를 피한다.
<<<
ASIL: QM
CATEGORY: 인터페이스
VERIFICATION: T
RELATIONS:
- TYPE: Parent
  VALUE: STK012
- TYPE: Parent
  VALUE: STK019
- TYPE: Parent
  VALUE: STK020

[REQUIREMENT]
UID: SYS031
TITLE: CAN 통신 - 메인 ECU → GUI (HMI 표시 데이터)
STATEMENT: >>>
메인 ECU(MPC5606B)는 ACC 상태 피드백을 CAN 메시지 ACC_STATUS(0x520)로 RPi GUI에 전송한다. DLC: 4 Byte.
메시지 내용: 현재 ACC 상태 GET_ACC_STATE(Byte 0, 0=OFF/1=STANDBY/2=CRUISING/3=FOLLOWING/4=FAULT), 설정 최고속도 GET_ACC_SPD(Byte 1-2, int16 cm/s, -500~500), 현재 거리설정 단계 GET_ACC_LVL(Byte 3, 1/2/3).
자차 속도는 본 메시지에 포함하지 않는다. RPi 는 MTR_SPD_FB(0x300) 프레임의 GET_SPD_AVG 시그널을 직접 수신한다(SYS017/SYS019) — 속도 데이터 원천 단일화.
ECU 에러 상태는 별도 ECU_HEARTBEAT(0x410)의 ERR_ECU 시그널로 전송한다.
전송 주기: 50ms.
<<<
ASIL: QM
CATEGORY: 인터페이스
VERIFICATION: T
RELATIONS:
- TYPE: Parent
  VALUE: STK012
- TYPE: Parent
  VALUE: STK020

[[/SECTION]]

[[SECTION]]
TITLE: 운전자 인터페이스

[REQUIREMENT]
UID: SYS018
TITLE: 운전자 입력 인터페이스 (가상 GUI)
STATEMENT: >>>
시스템은 다음 운전자 입력을 수신한다 (RPi GUI 가상 버튼):

- ACC ON/OFF 토글 버튼
- SET 버튼 (STANDBY→현재속도로 재활성화)
- RES 버튼 (STANDBY→이전설정속도로 재활성화)
- 속도+ 버튼, 속도- 버튼
- 거리설정 1/2/3단계 버튼 (개별)
- 일시정지 버튼 (CRUISING/FOLLOWING→STANDBY)
- 브레이크 버튼 신호 (디지털 ON/OFF, 눌림 유지 시 지속 제동), 액셀 페달 신호

모든 버튼 입력은 GUI에서 CAN 메시지로 메인 ECU에 전달된다.
<<<
ASIL: QM
CATEGORY: 인터페이스
VERIFICATION: T
RELATIONS:
- TYPE: Parent
  VALUE: STK019
- TYPE: Parent
  VALUE: STK020

[REQUIREMENT]
UID: SYS019
TITLE: HMI 출력 인터페이스 (GUI 클러스터)
STATEMENT: >>>
RPi GUI가 HMI 클러스터 역할을 수행하며 다음을 표시한다:

- 현재 자차 속도 — MTR_SPD_FB(0x300, 10ms) GET_SPD_AVG 시그널 직접 수신 (HMI 는 50ms 타이머로 decimation)
- ACC 상태 (OFF / STANDBY / CRUISING / FOLLOWING / FAULT) — ACC_STATUS(0x520) GET_ACC_STATE
- 현재 설정된 최고속도 — ACC_STATUS GET_ACC_SPD
- 현재 거리설정 단계 (1/2/3) — ACC_STATUS GET_ACC_LVL
- FAULT 발생 시 경고 표시 (시간 여유 시 경고음) — ERR_ECU (ECU_HEARTBEAT 0x410)

상태에 따라 비활성 버튼은 그레이아웃 처리한다.
<<<
ASIL: QM
CATEGORY: 인터페이스
VERIFICATION: I
RELATIONS:
- TYPE: Parent
  VALUE: STK020
- TYPE: Parent
  VALUE: STK021

[REQUIREMENT]
UID: SYS029
TITLE: 버튼 가용성 관리
STATEMENT: >>>
시스템은 현재 ACC 상태에 따라 각 버튼의 활성/비활성 상태를 관리한다.
비활성 버튼 입력은 무시하며, HMI GUI에서 그레이아웃 표시한다.
| 상태 | 활성 버튼 | 비활성 버튼 |
| OFF | ACC ON/OFF | SET, RES, 속도+/-, 거리설정, 일시정지 |
| STANDBY | ACC ON/OFF, SET, RES, 거리설정 | 속도+/-, 일시정지 |
| CRUISING | ACC ON/OFF, 속도+/-, 거리설정, 일시정지 | SET, RES |
| FOLLOWING | ACC ON/OFF, 속도+/-, 거리설정, 일시정지 | SET, RES |
| FAULT | ACC ON/OFF | 나머지 전부 |
<<<
ASIL: QM
CATEGORY: 기능
VERIFICATION: T
RELATIONS:
- TYPE: Parent
  VALUE: STK021

[[/SECTION]]

[REQUIREMENT]
UID: SYS036
TITLE: MotorControl SWC 도입 (inner-loop 속도 PI)
STATEMENT: >>>
메인 ECU 소프트웨어는 MotorControl SWC를 별도로 구성한다.

역할:

- DistanceControl SWC의 목표 속도(TargetSpeedCmS)와 실제 속도(EgoSpeedCmS, MTR_SPD_FB.GET_SPD_AVG) 오차로 inner-loop 속도 PI 제어를 수행하여 PWM duty 산출 (ACC 활성 시, SWR034)
- PWM 출력 범위 클램핑 (SAF008)
- GUI AccelPwmDuty를 직접 PWM으로 출력 (STANDBY 수동 제어 시, PI 적분기 리셋)
- OFF/FAULT 상태에서 모터 출력을 0으로 강제 (PI 적분기 리셋)

MotorControl SWC는 DistanceControl SWC와 분리됨으로써 "바깥 거리 PID (DistanceControl, 20ms)"와 "안쪽 속도 PI + PWM 클램핑 (MotorControl, 10ms)"의 책임을 분리한다 (cascaded 제어, 단일 책임 원칙, ASIL-B 적용).
<<<
ASIL: B
CATEGORY: 아키텍처
VERIFICATION: I
RELATIONS:
- TYPE: Parent
  VALUE: STK012
- TYPE: Parent
  VALUE: STK013

[REQUIREMENT]
UID: SYS037
TITLE: OFF/STANDBY 상태 수동 액셀 제어
STATEMENT: >>>
OFF 또는 STANDBY 상태에서 운전자는 RPi GUI의 액셀 슬라이더(SET_ACCEL_PWM)를 통해 모터를 수동으로 제어할 수 있다. SET_ACCEL_PWM 값은 VEH_CTRL(0x120, 20ms 주기) CAN 메시지를 통해 메인 ECU에 전달되고, MotorControl SWC가 즉시 PWM으로 출력한다. 응답 시간 50ms 이내.

ACC 활성(CRUISING/FOLLOWING) 중에는 PID 제어가 우선하며 AccelPwmDuty는 무시된다. AccelPwmDuty가 0 초과인 경우 브레이크 오버라이드(SYS006)와 동일하게 STANDBY 전이 조건으로 간주한다 (SYS007, SWR003).
<<<
ASIL: QM
CATEGORY: 기능
VERIFICATION: T
RELATIONS:
- TYPE: Parent
  VALUE: STK008
- TYPE: Parent
  VALUE: STK019

[[SECTION]]
TITLE: 비기능 요구사항

[REQUIREMENT]
UID: SYS023
TITLE: AUTOSAR 준수
STATEMENT: >>>
SW 아키텍처는 AUTOSAR 계층 구조(ASW/RTE/BSW)를 따른다. mobilgene을 활용하여 AUTOSAR 설정 및 코드 생성을 수행한다.
<<<
ASIL: QM
CATEGORY: 비기능
VERIFICATION: I
RELATIONS:
- TYPE: Parent
  VALUE: STK014

[REQUIREMENT]
UID: SYS024
TITLE: MBD 기반 제어 설계
STATEMENT: >>>
거리/속도 제어 로직은 MATLAB/Simulink MBD로 설계하고, 자동 코드 생성을 통해 구현한다.
<<<
ASIL: QM
CATEGORY: 비기능
VERIFICATION: I
RELATIONS:
- TYPE: Parent
  VALUE: STK014

[[/SECTION]]

[[SECTION]]
TITLE: 기타 기능

[REQUIREMENT]
UID: SYS026
TITLE: 직진 전용 차량
STATEMENT: >>>
차량은 조향 없이 직진만 가능하도록 설계된다. 차선 유지(LKAS) 기능은 본 시스템 범위에 포함되지 않는다.
<<<
ASIL: QM
CATEGORY: 기능
VERIFICATION: I
RELATIONS:
- TYPE: Parent
  VALUE: STK011

[REQUIREMENT]
UID: SYS027
TITLE: SET/RES에 의한 STANDBY 복귀
STATEMENT: >>>
STANDBY 상태에서의 복귀 동작:

- SET 버튼: 현재 주행 속도를 최고속도로 설정하고, 전방 차량 감지 시 FOLLOWING, 미감지 시 CRUISING으로 전이
- RES 버튼: 이전 설정 최고속도를 복원하고, 전방 차량 감지 시 FOLLOWING, 미감지 시 CRUISING으로 전이

SET/RES 버튼은 STANDBY 상태에서만 유효하며, 다른 상태에서는 비활성(그레이아웃).
<<<
ASIL: QM
CATEGORY: 기능
VERIFICATION: T
RELATIONS:
- TYPE: Parent
  VALUE: STK018
- TYPE: Parent
  VALUE: STK019
- TYPE: Parent
  VALUE: STK021

[REQUIREMENT]
UID: SYS028
TITLE: 일시정지 버튼 동작
STATEMENT: >>>
CRUISING 또는 FOLLOWING 상태에서 일시정지 버튼을 누르면 STANDBY로 전이한다. 이전 설정 속도와 안전거리 단계를 보존한다. 일시정지 버튼은 CRUISING/FOLLOWING 상태에서만 유효하며, 다른 상태에서는 비활성(그레이아웃).
<<<
ASIL: QM
CATEGORY: 기능
VERIFICATION: T
RELATIONS:
- TYPE: Parent
  VALUE: STK019
- TYPE: Parent
  VALUE: STK021

[REQUIREMENT]
UID: SYS032
TITLE: 최소 설정 속도 제한
STATEMENT: >>>
ACC 활성화(OFF→CRUISING/FOLLOWING) 또는 STANDBY에서 SET 복귀 시, 현재 자차 속도가 최소 설정 속도(5cm/s) 미만이면 최소 설정 속도를 최고속도로 자동 설정한다. RES 복귀 시에는 이전 설정 속도가 이미 최소값 이상이므로 별도 처리 불필요.
<<<
ASIL: QM
CATEGORY: 기능
VERIFICATION: T
RELATIONS:
- TYPE: Parent
  VALUE: STK022
- TYPE: Parent
  VALUE: STK024

[REQUIREMENT]
UID: SYS034
TITLE: ACC 활성화 시 기본 안전거리 단계
STATEMENT: >>>
ACC OFF에서 활성화(CRUISING/FOLLOWING) 전이 시, 안전거리 단계를 기본값 3단계(원거리)로 초기화한다. 이는 최초 활성화 시 가장 보수적인 차간거리를 적용하여 안전을 확보하기 위함이다.
<<<
ASIL: QM
CATEGORY: 기능
VERIFICATION: T
RELATIONS:
- TYPE: Parent
  VALUE: STK006
- TYPE: Parent
  VALUE: STK022

[REQUIREMENT]
UID: SYS033
TITLE: 페달 입력 중 ACC 활성화 거부
STATEMENT: >>>
브레이크 버튼 또는 액셀 페달이 눌려있는 상태에서 ACC ON/OFF 토글 버튼이 눌리면 ACC 활성화를 거부하고 OFF 상태를 유지한다.
이는 운전자가 직접 제어 중일 때 ACC가 의도치 않게 개입하는 것을 방지하기 위함이다.
브레이크 버튼 또는 액셀 페달을 뗀 후 다시 ACC ON/OFF를 눌러야 활성화가 가능하다.
<<<
ASIL: B
CATEGORY: 안전
VERIFICATION: T
RELATIONS:
- TYPE: Parent
  VALUE: STK007
- TYPE: Parent
  VALUE: STK008
- TYPE: Parent
  VALUE: STK022

[[/SECTION]]
