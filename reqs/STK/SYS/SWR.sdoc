[DOCUMENT]
TITLE: ACC Software Requirements (SWR)

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: TITLE
    TYPE: String
    REQUIRED: False
  - TITLE: STATEMENT
    TYPE: String
    REQUIRED: True
  - TITLE: ASIL
    TYPE: String
    REQUIRED: False
  - TITLE: CATEGORY
    TYPE: String
    REQUIRED: False
  - TITLE: VERIFICATION
    TYPE: String
    REQUIRED: False
  - TITLE: SWC
    TYPE: String
    REQUIRED: False
  - TITLE: COMMENT
    TYPE: String
    REQUIRED: False
  RELATIONS:
  - TYPE: Parent

[[SECTION]]
TITLE: AccStateMachine

[REQUIREMENT]
UID: SWR001
TITLE: ACC 상태 머신 구현
STATEMENT: >>>
ACC StateMachine SWC는 OFF, STANDBY, CRUISING, FOLLOWING, FAULT 5개 상태를 관리한다.

- OFF→CRUISING/FOLLOWING: ACC ON + 자가진단 통과 (현재 속도를 최고속도로 설정)
- STANDBY→CRUISING/FOLLOWING: SET 또는 RES 버튼
- CRUISING↔FOLLOWING: 전방 차량 감지/소멸
- CRUISING/FOLLOWING→STANDBY: 브레이크, 액셀, 일시정지
- Any Active→FAULT: 고장 감지
- FAULT→OFF: ACC ON/OFF 토글
- Any→OFF: ACC ON/OFF 토글
<<<
ASIL: >>>
B
<<<
CATEGORY: >>>
기능
<<<
VERIFICATION: >>>
T
<<<
SWC: >>>
AccStateMachine
<<<
RELATIONS:
- TYPE: Parent
  VALUE: SYS001
- TYPE: Parent
  VALUE: SYS002
- TYPE: Parent
  VALUE: SYS003
- TYPE: Parent
  VALUE: SYS004
- TYPE: Parent
  VALUE: SYS005

[REQUIREMENT]
UID: SWR002
TITLE: 브레이크 오버라이드 처리 (→ STANDBY)
STATEMENT: >>>
브레이크 버튼 신호(BTN_BRAKE)가 Active(1)이면 현재 상태와 무관하게 즉시 STANDBY 전이. 브레이크 버튼은 디지털 입력이며, 눌려있는 동안 지속적으로 제동 상태로 간주한다. 처리 지연 50ms 이내. 10ms 주기 태스크에서 브레이크 상태를 확인한다. STANDBY 전이 시 설정 속도 및 안전거리 단계 값을 내부 변수에 보존한다.
<<<
ASIL: B
CATEGORY: 안전
VERIFICATION: T
SWC: AccStateMachine
RELATIONS:
- TYPE: Parent
  VALUE: SYS006

[REQUIREMENT]
UID: SWR003
TITLE: 가속 오버라이드 처리 (→ STANDBY)
STATEMENT: >>>
액셀 페달 신호가 Active이면 현재 상태와 무관하게 즉시 STANDBY 전이. 이전 설정 속도와 안전거리 단계를 보존한다. 액셀 오버라이드 응답 시간은 50ms 이내.
<<<
ASIL: QM
CATEGORY: 기능
VERIFICATION: T
SWC: AccStateMachine
RELATIONS:
- TYPE: Parent
  VALUE: SYS007

[REQUIREMENT]
UID: SWR026
TITLE: SET/RES 버튼 처리
STATEMENT: >>>
STANDBY 상태에서:

- SET 버튼 수신 시: 현재 자차 속도를 최고속도로 설정, 전방 차량 유무에 따라 CRUISING/FOLLOWING 전이
- RES 버튼 수신 시: 보존된 이전 최고속도를 복원, 전방 차량 유무에 따라 CRUISING/FOLLOWING 전이

SET/RES는 STANDBY에서만 유효하며, 다른 상태에서 수신 시 무시한다.
<<<
ASIL: QM
CATEGORY: 기능
VERIFICATION: T
SWC: AccStateMachine
RELATIONS:
- TYPE: Parent
  VALUE: SYS027

[REQUIREMENT]
UID: SWR027
TITLE: 일시정지 버튼 처리
STATEMENT: >>>
CRUISING 또는 FOLLOWING 상태에서 일시정지 버튼 CAN 메시지 수신 시 STANDBY로 전이한다. 이전 설정 속도와 안전거리 단계를 보존한다. 일시정지 버튼은 CRUISING/FOLLOWING 상태에서만 유효하며, 다른 상태에서는 무시한다.
<<<
ASIL: QM
CATEGORY: 기능
VERIFICATION: T
SWC: AccStateMachine
RELATIONS:
- TYPE: Parent
  VALUE: SYS028

[REQUIREMENT]
UID: SWR028
TITLE: 버튼 가용성 상태 관리
STATEMENT: >>>
현재 ACC 상태에 따라 각 버튼의 활성/비활성 플래그를 관리한다. 비활성 버튼의 CAN 메시지가 수신되면 해당 입력을 무시한다. 버튼 가용성 정보를 HMI GUI로 CAN 전송하여 그레이아웃 표시에 활용한다.
<<<
ASIL: QM
CATEGORY: 기능
VERIFICATION: T
SWC: AccStateMachine
RELATIONS:
- TYPE: Parent
  VALUE: SYS029

[REQUIREMENT]
UID: SWR029
TITLE: ACC ON 자가진단
STATEMENT: >>>
ACC ON/OFF 토글 수신 시 (OFF→ON 방향), 다음 사전 조건 및 자가진단을 수행한다:

사전 조건 확인:

- 브레이크 버튼(BTN_BRAKE)/액셀 페달 입력 확인 → 눌려있으면 활성화 거부 (OFF 유지)

자가진단:

- CAN 통신 상태 확인 (각 노드 정상 응답)
- 센서 데이터 유효성 확인 (LiDAR, 카메라, 인코더)

자가진단 통과 시 안전거리 단계를 기본값 3단계(원거리)로 초기화한다.
자가진단 실패 시 ACC를 켜지 않고 OFF 상태를 유지하며, HMI에 진단 실패 메시지를 표시한다.
<<<
ASIL: B
CATEGORY: 안전
VERIFICATION: T
SWC: AccStateMachine
RELATIONS:
- TYPE: Parent
  VALUE: SYS001
- TYPE: Parent
  VALUE: SYS005
- TYPE: Parent
  VALUE: SYS033
- TYPE: Parent
  VALUE: SYS034

[REQUIREMENT]
UID: SWR031
TITLE: 최소 설정 속도 클램핑
STATEMENT: >>>
ACC 활성화 시 설정 최고속도를 max(현재속도, 5cm/s)로 클램핑한다. 최소설정속도는 5cm/s이다. 속도+/- 버튼으로 조정 시에도 최소설정속도 이하로 내려가지 않도록 제한한다.
<<<
ASIL: QM
CATEGORY: 기능
VERIFICATION: T
SWC: AccStateMachine
RELATIONS:
- TYPE: Parent
  VALUE: SYS032

[[/SECTION]]

[[SECTION]]
TITLE: SensorProcessing

[REQUIREMENT]
UID: SWR004
TITLE: LiDAR 거리 데이터 수신
STATEMENT: >>>
CAN RX로 수신된 LiDAR 거리값(VEH_DIST, 16bit uint, mm 단위, 0~12000)을 내부 변수에 저장한다. 메시지 타임아웃(60ms 미수신) 또는 ERR_SENSOR 시그널이 0이 아닌 경우 센서 이상 플래그를 설정한다.
<<<
ASIL: B
CATEGORY: 기능
VERIFICATION: T
SWC: SensorProcessing
RELATIONS:
- TYPE: Parent
  VALUE: SYS015
- TYPE: Parent
  VALUE: SYS025

[REQUIREMENT]
UID: SWR007
TITLE: 자차 속도 수신 및 처리
STATEMENT: >>>
모터 제어기(Arduino CAN 게이트웨이)에서 CAN RX로 수신된 인코더 기반 속도값을 처리한다. 실측 속도는 모터 노드가 I2C로 게이트웨이에 전달한 값이 CAN으로 중계된 것이며, 타임아웃 시 속도 이상 플래그를 설정한다.
<<<
ASIL: QM
CATEGORY: 기능
VERIFICATION: T
SWC: SensorProcessing
RELATIONS:
- TYPE: Parent
  VALUE: SYS012
- TYPE: Parent
  VALUE: SYS017

[[/SECTION]]

[[SECTION]]
TITLE: DistanceControl

[REQUIREMENT]
UID: SWR008
TITLE: 안전거리 목표값 계산 (AEB 미포함)
STATEMENT: >>>
현재 선택된 안전거리 단계(1~3)와 자차 속도를 기반으로 목표 차간거리를 계산한다. 단계별 Time-gap 계수: 1단계=0.8s, 2단계=1.2s, 3단계=1.6s. 목표 거리 이하 접근 시 PID 제어 범위 내에서 최대 감속을 수행한다. 비상 제동(AEB)은 수행하지 않는다.
<<<
ASIL: >>>
B
<<<
CATEGORY: >>>
기능
<<<
VERIFICATION: >>>
T
<<<
SWC: >>>
DistanceControl
<<<
RELATIONS:
- TYPE: Parent
  VALUE: SYS008
- TYPE: Parent
  VALUE: SYS009
- TYPE: Parent
  VALUE: SYS010
- TYPE: Parent
  VALUE: SYS022
- TYPE: Parent
  VALUE: SYS035

[REQUIREMENT]
UID: SWR009
TITLE: DistanceControl outer-loop 제어 (거리 PID)
STATEMENT: >>>
Simulink MBD에서 생성된 PID 제어 코드를 실행한다. 출력: IF_CtrlOutput (TargetSpeedCmS, CtrlMode, CmdValid) — MotorControl SWC로 전달. 제어 주기: 20ms (Task_20ms, SWR022). FOLLOWING 모드에서 거리 오차에 대한 이산 PID + back-calculation anti-windup 을 수행하고, CRUISING 모드에서는 TargetSpeedCmS = SetSpeedCmS 로 직접 전달한다(outer-loop 불필요). 속도 inner-loop PI 는 MotorControl SWC 가 담당 (SWR034).

cascaded 구조: DistanceControl(20ms, 거리→목표속도) → MotorControl(10ms, 목표속도→PWM). 두 루프 주기 2× 분리로 대역폭 간섭 최소화.
<<<
ASIL: QM
CATEGORY: 기능
VERIFICATION: T
SWC: DistanceControl
RELATIONS:
- TYPE: Parent
  VALUE: SYS014
- TYPE: Parent
  VALUE: SYS024

[REQUIREMENT]
UID: SWR010
TITLE: CRUISE 모드 목표속도 직접 전달
STATEMENT: >>>
CRUISE 상태에서는 DistanceControl 이 outer-loop PID 를 수행하지 않고 TargetSpeedCmS = SetSpeedCmS 로 직접 전달한다. 속도 추종은 MotorControl SWC 의 inner-loop 속도 PI (SWR034) 가 담당한다. 전방 차량 감지 시 FOLLOWING 전환 트리거를 StateMachine에 전달한다.
<<<
ASIL: QM
CATEGORY: 기능
VERIFICATION: T
SWC: DistanceControl
RELATIONS:
- TYPE: Parent
  VALUE: SYS003
- TYPE: Parent
  VALUE: SYS014

[REQUIREMENT]
UID: SWR011
TITLE: FOLLOWING 모드 거리 제어 (outer-loop)
STATEMENT: >>>
FOLLOWING 상태에서 목표 차간거리(SWR008)를 유지하도록 거리 PID 를 수행하여 TargetSpeedCmS 를 산출한다.

알고리즘: TargetSpeedCmS = clamp( SetSpeedCmS + DistPID(FwdDistance − SafeDistance), 0, SetSpeedCmS ). 거리가 부족하면 감속하고 SetSpeedCmS 이상으로 증속하지 않으며, 하한은 0 (후진 금지).

출력 단위는 속도 (cm/s) — MotorControl SWC 의 inner-loop (SWR034) 가 이를 받아 PWM 으로 변환. 전방 차량 소멸 시 CRUISE 전환 트리거를 StateMachine에 전달한다.
<<<
ASIL: B
CATEGORY: 기능
VERIFICATION: T
SWC: DistanceControl
RELATIONS:
- TYPE: Parent
  VALUE: SYS004
- TYPE: Parent
  VALUE: SYS014

[[/SECTION]]

[[SECTION]]
TITLE: CanCommunication

[REQUIREMENT]
UID: SWR012
TITLE: CAN TX - 모터 제어 명령 송신
STATEMENT: >>>
MotorControl SWC가 IF_MotorCmd (TargetPwmDuty, CmdValid)를 생성하면, CanCommunication SWC의 RE_CanTxMotor (10ms)가 이를 MTR_CMD(0x210) CAN 메시지로 Arduino CAN 게이트웨이에 전송한다. CAN 페이로드는 DBC 정본을 유지해 4휠(앞좌/앞우/뒤좌/뒤우) 시그널을 그대로 싣되 모든 채널에 동일한 TargetPwmDuty 값을 복제해 송신한다. 게이트웨이는 I2C로 모터 노드에 명령을 중계하며, 모터 노드는 대표 바퀴 1개에만 실제 PWM 출력을 적용한다(스케일카 시연 단순화). DLC: 6 bytes (PWM 4ch × 1byte + MTR_RC 4bit + MTR_CRC 8bit, E2E P01 per SAF010 ASIL-B).
<<<
ASIL: QM
CATEGORY: 인터페이스
VERIFICATION: T
SWC: CanCommunication
RELATIONS:
- TYPE: Parent
  VALUE: SYS016

[REQUIREMENT]
UID: SWR013
TITLE: CAN RX - 센서 데이터 수신
STATEMENT: >>>
카메라+LiDAR 처리 유닛으로부터 전방 차량 정보(SENSOR_FUSION 0x110: VEH_DET, VEH_DIST) CAN 메시지를 수신한다. 상대속도는 ECU 내부에서 산출(SYS013)하므로 수신 시그널에 포함되지 않는다. 수신 주기: 20ms. 타임아웃: 60ms.
<<<
ASIL: QM
CATEGORY: 인터페이스
VERIFICATION: T
SWC: CanCommunication
RELATIONS:
- TYPE: Parent
  VALUE: SYS015

[REQUIREMENT]
UID: SWR014
TITLE: CAN RX - 모터 피드백 수신
STATEMENT: >>>
모터 제어기(Arduino CAN 게이트웨이)로부터 실측 속도, 모터 상태 CAN 메시지를 수신한다. 실측값은 모터 노드가 단일 엔코더로 측정한 대표 바퀴 1개의 속도이며, I2C로 게이트웨이에 전달 후 DBC 정본 포맷(4휠 속도)의 모든 채널에 동일 값으로 복제되어 CAN 송신된다. 30ms 타임아웃은 CAN + I2C 종단간을 포괄한다. 수신 주기: 10ms.
<<<
ASIL: QM
CATEGORY: 인터페이스
VERIFICATION: T
SWC: CanCommunication
RELATIONS:
- TYPE: Parent
  VALUE: SYS017

[REQUIREMENT]
UID: SWR015
TITLE: CAN 메시지 타임아웃 감시
STATEMENT: >>>
각 CAN RX 메시지에 대해 타임아웃 카운터를 관리한다. 모터 피드백의 경우 CAN 게이트웨이 ↔ 모터 노드 간 I2C 단절도 MTR_SPD_FB 미수신 형태로 관찰되어 동일한 타임아웃 메커니즘으로 감지된다(종단간). 타임아웃 발생 시 해당 데이터를 무효화하고 Diagnostics SWC에 에러를 보고한다. 또한, 각 노드의 에러코드 시그널(ERR_SENSOR, ERR_MTR, ERR_ECU)을 모니터링하여 0이 아닌 값 수신 시 해당 노드 고장으로 판단하고 Diagnostics SWC에 보고한다.
<<<
ASIL: B
CATEGORY: 안전
VERIFICATION: T
SWC: CanCommunication
RELATIONS:
- TYPE: Parent
  VALUE: SYS025

[[/SECTION]]

[[SECTION]]
TITLE: Diagnostics

[REQUIREMENT]
UID: SWR016
TITLE: 고장 감지 및 FAULT 전이 (능동 감속 없음)
STATEMENT: >>>
센서 이상(ERR_SENSOR != 0), 모터 이상(ERR_MTR != 0), ECU 내부 이상(ERR_ECU != 0), CAN 타임아웃을 감지하면 StateMachine에 FAULT 전이를 요청한다. FAULT 진입 시 모터 제어 출력을 0으로 설정한다 (능동 감속 없음). HMI에 FAULT 경고를 즉시 전달하며, 에러코드 값을 포함하여 고장 원인을 식별할 수 있도록 한다. FAULT 상태에서는 ACC ON/OFF 토글만 처리하며(→ OFF), 그 외 입력은 무시한다.
<<<
ASIL: B
CATEGORY: 안전
VERIFICATION: T
SWC: Diagnostics
RELATIONS:
- TYPE: Parent
  VALUE: SYS005
- TYPE: Parent
  VALUE: SYS025

[[/SECTION]]

[[SECTION]]
TITLE: HmiManager

[REQUIREMENT]
UID: SWR018
TITLE: HMI GUI 표시 (클러스터)
STATEMENT: >>>
RPi에서 실행되는 GUI 애플리케이션을 통해 현재 ACC 상태, 설정 속도, 안전거리 단계, 전방 차량 감지, 자차 속도를 표시한다. 데이터 원천:

- ACC 관련 상태/설정: 메인 ECU → ACC_STATUS(0x520) 수신 (50ms 주기).
- 자차 속도: MTR(Arduino) → MTR_SPD_FB(0x300) GET_SPD_AVG 시그널 직접 수신 (프레임 10ms, HMI 는 50ms 로 decimation).
- ECU 에러/HB: ECU_HEARTBEAT(0x410) 의 ERR_ECU.

GUI 갱신 주기: 50ms. 상태별 버튼 그레이아웃 처리를 수행한다.
<<<
ASIL: QM
CATEGORY: 기능
VERIFICATION: I
SWC: HmiManager
RELATIONS:
- TYPE: Parent
  VALUE: SYS019

[REQUIREMENT]
UID: SWR019
TITLE: FAULT 경고 표시
STATEMENT: >>>
FAULT 상태 진입 시 GUI에 경고 메시지를 즉시 표시한다. 경고는 운전자가 ACC ON/OFF를 눌러 OFF 전이 시 해제된다. 시간 여유 시 경고음(buzzer 또는 SW audio)을 추가한다.
<<<
ASIL: QM
CATEGORY: 안전
VERIFICATION: T
SWC: HmiManager
RELATIONS:
- TYPE: Parent
  VALUE: SYS005
- TYPE: Parent
  VALUE: SYS019

[[/SECTION]]

[[SECTION]]
TITLE: DriverInput

[REQUIREMENT]
UID: SWR020
TITLE: 운전자 입력 처리 (GUI → CAN)
STATEMENT: >>>
PyQt GUI 버튼/슬라이더 이벤트를 두 CAN 메시지로 분리하여 메인 ECU에 전송한다.

**VEH_CTRL(0x120, 20ms 주기)** — 차량 직접 조작:

- 브레이크(BTN_BRAKE, 1bit @ Byte 1 [0]): 디바운싱 없이 즉시 처리. 눌림 유지 시 레벨 트리거 (SAF004 ASIL-B).
- 액셀 슬라이더(SET_ACCEL_PWM, int8 @ Byte 0, -128~127): GUI 슬라이더 현재값을 매 주기 그대로 전송. 디바운싱 없음. 음수는 후진 PWM(확장 옵션). STANDBY 상태에서 MotorControl SWC가 직접 PWM으로 사용 (SWR033).

**ACC_CTRL(0x510, 50ms 주기)** — ACC feature:

- 버튼(BTN_ACC_OFF/SET/RES/CANCEL, 각 1bit @ Byte 0 bits 0-3): 300ms 디바운싱 적용. 엣지 트리거 — TX 후 자동 클리어.
- 설정 속도(SET_ACC_SPD, int16 @ Byte 1-2): GUI 가 현재값±증분 계산해 절대값 전송.
- 거리 단계(SET_ACC_LVL, uint8 @ Byte 3, 1/2/3): 거리 버튼 클릭 시 해당 단계 값.
<<<
ASIL: QM
CATEGORY: 기능
VERIFICATION: T
SWC: DriverInput
RELATIONS:
- TYPE: Parent
  VALUE: SYS018
- TYPE: Parent
  VALUE: SYS030

[[/SECTION]]

[[SECTION]]
TITLE: AUTOSAR OS 태스크

[REQUIREMENT]
UID: SWR021
TITLE: 태스크 주기 - 10ms
STATEMENT: >>>
10ms 주기 태스크에서 다음을 수행한다: AccStateMachine FSM 전이 평가, MotorControl inner-loop 속도 PI (SWR034), CanCommunication 모터 송수신 (MTR_CMD/MTR_SPD_FB), ECU_HEARTBEAT 송신, Diagnostics 고장 감지. 브레이크/액셀 감시는 FSM 내부에서 10ms tick 으로 수행.

cascaded 제어 구조에서 10ms 는 안쪽 (속도) 루프, 20ms 는 바깥 (거리) 루프 (SWR022). 두 루프 주기 비율 2× 로 대역폭 간섭 최소화.
<<<
ASIL: B
CATEGORY: 타이밍
VERIFICATION: T
SWC: AUTOSAR_OS
RELATIONS:
- TYPE: Parent
  VALUE: SYS014
- TYPE: Parent
  VALUE: SYS020

[REQUIREMENT]
UID: SWR022
TITLE: 태스크 주기 - 20ms
STATEMENT: >>>
20ms 주기 태스크에서 다음을 수행한다: DistanceControl outer-loop 거리 PID (SWR009/011), 센서 데이터 수신 처리(SENSOR_FUSION 0x110 — LiDAR+카메라 융합 결과), 차량 직접 조작 입력 수신 처리(VEH_CTRL 0x120 — 브레이크/수동 액셀).

DistanceControl 을 20ms 로 배치한 이유:
- SENSOR_FUSION 입력 갱신 주기(20ms)와 일치 — Rte_Read 가 stale 하지 않음
- cascaded 제어에서 바깥 루프를 안쪽 (10ms, MotorControl PI) 의 2× 주기로 분리 — 대역폭 간섭 최소화 (SWR034 참조)

VEH_CTRL 은 SAF004/SAF015 ASIL-B 경로이며 50ms 응답 요건 때문에 20ms 주기 태스크에 배치.
<<<
ASIL: QM
CATEGORY: 타이밍
VERIFICATION: T
SWC: AUTOSAR_OS
RELATIONS:
- TYPE: Parent
  VALUE: SYS021

[REQUIREMENT]
UID: SWR023
TITLE: 태스크 주기 - 50ms / 100ms
STATEMENT: >>>
- Task_50ms (QM): HMI 갱신 처리 — CanComm.RE_CanRxAccCtrl (ACC_CTRL 0x510 수신), HmiManager.RE_BtnDispatch/RE_StatusBuild, CanComm.RE_CanTxAccStatus (ACC_STATUS 0x520 송신).
- Task_100ms (QM): 진단 보고 처리 — Diagnostics.RE_DtcReport.
<<<
ASIL: QM
CATEGORY: 타이밍
VERIFICATION: T
SWC: AUTOSAR_OS
RELATIONS:
- TYPE: Parent
  VALUE: SYS019

[[/SECTION]]

[[SECTION]]
TITLE: 코드 품질 및 아키텍처

[REQUIREMENT]
UID: SWR024
TITLE: MISRA-C:2012 준수
STATEMENT: >>>
모든 수동 작성 C 코드는 MISRA-C:2012 규칙을 준수한다. Mandatory/Required 규칙 위반 0건을 목표로 한다. Advisory는 편차 기록 후 허용.
<<<
ASIL: B
CATEGORY: 비기능
VERIFICATION: A
SWC: All
RELATIONS:
- TYPE: Parent
  VALUE: SYS023

[REQUIREMENT]
UID: SWR025
TITLE: AUTOSAR RTE 포트 정의
STATEMENT: >>>
각 SWC 간 데이터 교환은 AUTOSAR RTE Sender-Receiver 또는 Client-Server 포트를 통해 수행한다. mobilgene으로 AUTOSAR 설정 및 RTE 코드를 생성한다.
<<<
ASIL: QM
CATEGORY: 비기능
VERIFICATION: I
SWC: All
RELATIONS:
- TYPE: Parent
  VALUE: SYS023

[[/SECTION]]

[[SECTION]]
TITLE: MotorControl

[REQUIREMENT]
UID: SWR032
TITLE: MotorControl SWC 구현 (상태별 제어 분기)
STATEMENT: >>>
MotorControl SWC는 RE_MotorCtrlStep(10ms, Task_10ms) 런너블에서 현재 ACC 상태에 따라 IF_MotorCmd(TargetPwmDuty, CmdValid)를 생성한다.

제어 분기:

- CRUISING / FOLLOWING: inner-loop 속도 PI (SWR034) 를 수행. 입력: RP_CtrlOutput.TargetSpeedCmS (DistanceControl 산출) + RP_SensorData.EgoSpeedCmS (MTR_SPD_FB.GET_SPD_AVG). 출력: PWM = FF_Lookup(target) + PI(target − ego), SAF008 [-PWM_MAX, +PWM_MAX] 클램핑. FF_Lookup 은 벤치 튜닝 전까지 0 (순수 PI).
- STANDBY: RP_HmiBtn.AccelPwmDuty를 직접 TargetPwmDuty로 출력 (SWR033), PI 적분기 리셋.
- OFF / FAULT: TargetPwmDuty = 0, CmdValid = false, PI 적분기 리셋.

포트:

- PP: PP_MotorCmd (IF_MotorCmd → CanCommunication)
- RP: RP_CtrlOutput (IF_CtrlOutput ← DistanceControl), RP_SensorData (IF_SensorData ← CanCommunication, EgoSpeedCmS 만 사용), RP_AccStatus (IF_AccStatus ← AccStateMachine), RP_HmiBtn (IF_HmiBtn ← CanCommunication), RP_WdgM (CS_WdgM)
<<<
ASIL: B
CATEGORY: 기능
VERIFICATION: T
SWC: MotorControl
RELATIONS:
- TYPE: Parent
  VALUE: SYS016
- TYPE: Parent
  VALUE: SYS036

[REQUIREMENT]
UID: SWR033
TITLE: OFF/STANDBY 수동 액셀 PWM 제어
STATEMENT: >>>
OFF 또는 STANDBY 상태에서 MotorControl SWC는 RP_HmiBtn.AccelPwmDuty를 읽어 즉시 TargetPwmDuty로 출력한다. 응답 시간 50ms 이내 (10ms Task 주기 + CAN 전달 지연). AccelPwmDuty = 0이면 모터 정지. ACC 활성(CRUISING/FOLLOWING) 상태로 전이 시 DistanceControl 제어 출력으로 전환. STANDBY 진입 시 inner-loop PI 적분기를 리셋하여 ACC 재진입 시 bump 방지 (SWR034). FAULT 상태에서는 안전을 위해 강제 PWM=0 을 출력한다.
<<<
ASIL: QM
CATEGORY: 기능
VERIFICATION: T
SWC: MotorControl
RELATIONS:
- TYPE: Parent
  VALUE: SYS037
- TYPE: Parent
  VALUE: SYS036

[REQUIREMENT]
UID: SWR034
TITLE: MotorControl inner-loop 속도 PI 제어
STATEMENT: >>>
MotorControl SWC 는 CRUISING/FOLLOWING 상태에서 목표 속도(TargetSpeedCmS)와 실제 속도(EgoSpeedCmS, 대표 속도로 MTR_SPD_FB.GET_SPD_AVG 시그널 사용)의 오차를 입력으로 이산 PI 제어를 수행하여 PWM duty 를 산출한다.

알고리즘:

- err = TargetSpeedCmS − EgoSpeedCmS
- u_unsat = FF_Lookup(TargetSpeedCmS) + Kp·err + integ
- u_sat = clamp(u_unsat, −PWM_MAX, +PWM_MAX)  (SAF008)
- integ ← integ + Ki·err·Ts + KB_AW·(u_sat − u_unsat)  (back-calculation anti-windup)
- TargetPwmDuty = u_sat

제어 주기: 10ms (Task_10ms, SWR021).

Anti-windup 및 모드 전환 처리:

- STANDBY/OFF/FAULT 진입 시 integ 및 prev_error 를 0 으로 리셋 (bump-less 전환)
- 적분기 포화 [−INTEG_MAX, +INTEG_MAX] 클램프
- 포화 상태에서 back-calculation 으로 integ wind-up 방지

FF_Lookup (feedforward): 벤치 테스트로 PWM→정상속도 매핑이 확보되기 전까지 0 (순수 PI). 확보 후 속도→PWM 선형 또는 구간별 lookup 으로 교체 (SAF008 클램핑은 유지).

cascaded 구조: 바깥 거리 PID (SWR011, 20ms, DistanceControl) → TargetSpeedCmS → 안쪽 속도 PI (본 SWR, 10ms, MotorControl) → PWM. 두 루프 주기 비율 2× 로 대역폭 분리.

게인 Kp/Ki 및 FF_Lookup 은 HIL 단계에서 TODO_TUNE.
<<<
ASIL: B
CATEGORY: 기능
VERIFICATION: T
SWC: MotorControl
RELATIONS:
- TYPE: Parent
  VALUE: SYS014
- TYPE: Parent
  VALUE: SYS036

[[/SECTION]]

[[SECTION]]
TITLE: GuiCanInterface

[REQUIREMENT]
UID: SWR030
TITLE: GUI-CAN 인터페이스 (RPi측)
STATEMENT: >>>
RPi에서 실행되는 GUI 애플리케이션은:

- 운전자 버튼 클릭 → CAN TX 메시지 생성 (20ms 주기)
- 메인 ECU로부터 CAN RX 메시지 수신 → GUI 화면 갱신 (50ms 주기)
- 카메라+LiDAR 처리 결과(전방 차량 정보)를 동일 CAN 버스로 전송

CAN 인터페이스는 USB-CAN 어댑터 또는 MCP2515 SPI-CAN 모듈을 사용한다.
<<<
ASIL: QM
CATEGORY: 인터페이스
VERIFICATION: T
SWC: GuiCanInterface
RELATIONS:
- TYPE: Parent
  VALUE: SYS015
- TYPE: Parent
  VALUE: SYS030
- TYPE: Parent
  VALUE: SYS031

[[/SECTION]]
